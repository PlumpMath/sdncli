/***********************************************************************
 *brocade-sec-services.yang: Brocade Security Services data model
 *
 * Jul 2012, Balaji. M
 *
 * Copyright (c) 2011-2012 by Brocade Communications Systems, Inc.
 * All rights reserved.
 *
 **********************************************************************/

module brocade-sec-services {
    namespace "urn:brocade.com:mgmt:brocade-sec-services";
    prefix "brcd-sec-services";

    import tailf-common {
        prefix tailf;
    }

    import brocade-common-def {
        prefix common-def;
    }

    import brocade-rbridge {
        prefix rbridge;
    }

    organization
        "Brocade Communications Systems, Inc.";

        contact
        "Brocade Communications Systems, Inc.
         Postal: 130 Holger Way
                 San Jose, CA 95134
                  U.S.A
         Tel: +1-408-333-8000
         E-mail: support@Brocade.com
         web: www.brocade.com.";

        description
        "Instrument to configure Telnet Server and SSH Server";

        revision "2012-07-28" {
        description
            "Initial version of this module.";
        }

    grouping telnet-group {
    container telnet {
        container server {
            leaf shutdown {
                // tailf:cli-show-no;
                type empty;
            }
            container standby {
                leaf enable {
                    type empty;
                }
            }
        }
    }
    }

    /* Define the "show telnet status" functionality */
    augment "/common-def:show" {
        container telnet {
            container server {
                tailf:action status {
                    input {
                        leaf rbridge-id {
                            mandatory false;
                            type common-def:rbridge-id-all-type;
                        }
                    }
                    output {
                    }
                }
            }
        }
    }

    augment "/rbridge:rbridge-id" {
        uses telnet-group;
    }

    container telnet-sa { 
        uses telnet-group;
    }

    typedef key-exchange-type {
        type enumeration {
            enum dh-group-14 {
                value 2;
            }
        }
    }

    typedef ssh_cipher_type {
        type enumeration {
            enum non-cbc {
                value 1;
            }
        }
    }

    typedef ecdsa-bits-size {
        type enumeration {
            enum 256 {
                value 256;
            }
        }
    }

    typedef rsa-bits-size {
        type enumeration {
            enum 1024 {
                value 1024;
            }
            enum 2048 {
                value 2048;
            }
        }
    }

    grouping ssh-group {
    container ssh {
        container server {
            leaf shutdown {
                // tailf:cli-show-no;
                type empty;
            }

            list key-exchange {
                key "protocol";
                leaf protocol {
                    type key-exchange-type;
                }
            }
            leaf rekey-interval {
                type uint32 {
                    range "900..3600" {
                    }
                }
            }
            leaf cipher {
                type ssh_cipher_type;
            }
            leaf mac {
                type string {
                    // pattern 'hmac-md5,hmac-sha1,hmac-sha2-256,hmac-sha2-512,hmac-sha1-96,hmac-md5-96';
                }
            }
            container standby {
                leaf enable {
                    type empty;
                }
            }
            container key {
                leaf rsa {
                    type rsa-bits-size;
                }
                
                leaf ecdsa {
                    type ecdsa-bits-size;
                }
                leaf dsa {
                    type empty;
                }
            }
        }
        container client {
            leaf cipher {
                type ssh_cipher_type;
            }
            leaf mac {
                type string {
                    // pattern 'hmac-md5,hmac-sha1,hmac-sha2-256,hmac-sha2-512,hmac-sha1-96,hmac-md5-96';
                }
            }
        }
    }
    }

    augment "/rbridge:rbridge-id" {
        uses ssh-group;
    }
            
    container ssh-sa {  
        uses ssh-group;
    }

    augment "/common-def:show" {
        container ssh {
            container server {
                tailf:action status {
                    input {
                        leaf rbridge-id {
                            mandatory false;
                            type common-def:rbridge-id-all-type;
                        }
                    }
                    output {
                    }
                }
            }
            container client {
                tailf:action status {
                    input {
                        leaf rbridge-id {
                            mandatory false;
                            type common-def:rbridge-id-all-type;
                        }
                    }
                    output {
                    }
                }
            }
        }
    }
}
