/***********************************************************************
 * brocade-ip-forward.yang: Brocade IP Forwarding data model.
 *
 * March  2011, Bhavin Patel
 *
 * Copyright (c) 2011 by Brocade Communications Systems, Inc.
 * All rights reserved.
 *
 **********************************************************************/
module brocade-ip-access-list {
    namespace "urn:brocade.com:mgmt:brocade-ip-access-list";
    prefix ip-access-list;

    import brocade-rbridge { prefix rbridge; }
    import brocade-interface { prefix interface; }
    import tailf-common {
        prefix tailf;
    }

    import ietf-inet-types {
        prefix "inet";
    }

    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "This management sub-module contains the configuration
        and rpc implementaion for IP Access-list.";

    revision "2011-03-01" {
       description "Initial version";
    }

    typedef l3-acl-policy-name {
        type string {
            pattern '[a-zA-Z0-9]{1}([-a-zA-Z0-9_]{0,62})' {
            }
            length 1..63;
        }
    }

    typedef ip-acl-ext-action-t {
	    type enumeration {
	        enum permit {
	            value 1;
	        }
	        enum deny {
	            value 2;
	        }
	        enum hard-drop {
	            value 3;
	        }
	    }
    }

    typedef seq-id-std-ext {
        type uint64 {
            range "0 .. 4294967290" {
            }
        }
    }

    typedef resequence-starting-seq-id {
        type uint64 {
            range "0 .. 4294967290" {
            }
        }
    }
    
    typedef resequence-increment-seq-id {
        type uint64 {
            range "1 .. 4294967290" {
            }
        }
    }
    
    typedef precedence-uint {
        type uint32 {
            range "0..7" {
            }
        }
    }

    typedef tos-uint {
        type uint32 {
            range "0..63" {
            }
        }
    }

    typedef dscp-uint {
        type uint32 {
            range "0..63" {
            }
        }
    }
    
    typedef sip {
        type inet:ipv4-address;
    }

    typedef sip-cidr {
        type inet:ipv4-prefix;
    }

    typedef dip {
        type inet:ipv4-address;
    }

    typedef dip-cidr {
        type inet:ipv4-prefix;
    }

    typedef dip-mask {
        type inet:ipv4-address;
    }    

    typedef sip-mask {
        type inet:ipv4-address;
    }

    typedef sport-number-eq-neq-tcp-udp {
        type uint32 {
            range "0 .. 65535" {
            }
        }
    }

    typedef sport-number-lt-tcp-udp {
        type uint32 {
            range "1 .. 65535" {
            }
        }
    }

    typedef sport-number-gt-tcp-udp {
        type uint32 {
            range "0 .. 65535" {
            }
        }
    }
    
    typedef sport-range-lower-tcp-udp {
        type uint32 {
            range "0 .. 65535" {
            }
        }
    }
    
    typedef sport-range-higher-tcp-udp {
        type uint32 {
            range "1 .. 65535" {
            }
        }
    }
    
    typedef dport-number-lt-tcp-udp {
        type uint32 {
            range "1 .. 65535" {
            }
        }
    }

    typedef dport-number-gt-tcp-udp {
        type uint32 {
            range "0 .. 65535" {
            }
        }
    }
    
    typedef dport-number-eq-neq-tcp-udp {
        type uint32 {
            range "0 .. 65535" {
            }
        }
    }
    
    typedef dport-range-lower-tcp-udp {
        type uint32 {
            range "0 .. 65535" {
            }
        }
    }
    
    typedef dport-range-higher-tcp-udp {
        type uint32 {
            range "1 .. 65535" {
            }
        }
    }
    
    typedef proto-type {
        type uint32 {
            range "0..255" {
            }
        }
    }

    typedef wellknown-port-tcp {
        type enumeration {
            enum echo {
                value 7;
            }
            enum daytime {
                value 13;
            }
            enum ftp-data {
                value 20;
            }
            enum ftp {
                value 21;
            }
            enum smtp {
                value 25;
            }
            enum telnet {
                value 23;
            }
            enum time {
                value 37;
            }
            enum tacacs {
                value 49;
            }
            enum domain {
                value 53;
            }
            enum www {
                value 80;
            }
            enum hostname {
                value 101;
            }
            enum bgp {
                value 179;
            }
            enum pim-auto-rp {
                value 496;
            }
            enum login {
                value 513;
            }
            enum syslog {
                value 514;
            }
            enum talk {
                value 517;
            }
        }
    }
    

    typedef wellknown-precedence {
        type enumeration {
            enum critical {
                value 5;
            }
            enum flash {
                value 3;
            }
            enum flash-override {
                value 4;
            }
            enum immediate {
                value 2;
            }
            enum internet {
                value 6;
            }
            enum network {
                value 7;
            }
            enum priority {
                value 1;
            }
            enum routine {
                value 0;
            }
        }
    }

    typedef wellknown-dscp {
        type enumeration {
            enum af11 {
                value 10;
            }
            enum af12 {
                value 12;
            }
            enum af13 {
                value 14;
            }
            enum af21 {
                value 18;
            }
            enum af22 {
                value 20;
            }
            enum af23 {
                value 22;
            }
            enum af31 {
                value 26;
            }
            enum af32 {
                value 28;
            }
            enum af33 {
                value 30;
            }
            enum af41 {
                value 34;
            }
            enum af42 {
                value 36;
            }
            enum af43 {
                value 38;
            }
            enum cs1 {
                value 8;
            }
            enum cs2 {
                value 16;
            }
            enum cs3 {
                value 24;
            }
            enum cs4 {
                value 32;
            }
            enum cs5 {
                value 40;
            }
            enum cs6 {
                value 48;
            }
            enum cs7 {
                value 56;
            }
            enum default {
                value 0;
            }
            enum ef {
                value 46;
            }
        }
    }

    typedef wellknown-tos {
        type enumeration {
            enum max-reliability {
                value 1;
            }
            enum max-throughput {
                value 2;
            }
            enum min-delay {
                value 4;
            }
            enum normal {
                value 0;
            }
        }
    }
        
    typedef wellknown-port-udp {
        type enumeration {
            enum echo {
                value 7;
            }
            enum tacacs {
                value 49;
            }
            enum domain {
                value 53;
            }
            enum bootps {
                value 67;
            }
            enum bootpc {
                value 68;
            }
            enum tftp {
                value 69;
            }
            enum ntp{
                value 123;
            }
            enum snmp{
                value 161;
            }
            enum pim-auto-rp {
                value 496;
            }
            enum syslog {
                value 514;
            }
            enum rip {
                value 520;
            }
        } // type enumeration
    } //typedef wellknown-port-udp

    grouping ip-ext-access-list-rule {
        leaf action {
            type enumeration {
                enum permit {
                    value 1;
                }
                enum deny {
                    value 2;
                }
                enum hard-drop {
                    value 3;
                }
            }
        }

        leaf protocol-type {
            type union {
                type enumeration {
                    enum icmp {
                        value 1;
                    }
                    enum ip {
                        value 4;
                    }
                    enum tcp {
                        value 6;
                    }
                    enum udp {
                        value 17;
                    }
                }
                type proto-type;
            }
            mandatory true;
        }

            
        leaf src-host-any-sip {
            type union {
                type enumeration {
                    enum any {
                        value 1;
                    }
                    enum host {
                        value 2;
                    }
                }
                type sip;
                type sip-cidr;
            }
            mandatory true;
        }

        leaf src-host-ip {
            when "../src-host-any-sip ='host'" {
            }
            type sip;
        }

        leaf src-mask {
            when "((../src-host-any-sip !='any') and 
                (../src-host-any-sip !='host') and 
                ((not(contains((../src-host-any-sip),'/')))))" {
            }
            type sip-mask;
        }
            
        leaf sport {
               when "((../protocol-type ='tcp') or 
                (../protocol-type ='udp') or 
                (../protocol-type ='6') or 
                (../protocol-type ='17'))" {
            }
            type enumeration {
                enum eq {
                    value 1;
                }
                enum gt {
                    value 2;
                } 
                enum lt {
                    value 3;
                }
                enum neq {
                    value 4;
                }
                enum range {
                    value 5;
                }
            } // type enumeration
        } //type sport
        
        leaf sport-number-eq-neq-tcp {
            when "(((../protocol-type ='tcp') or 
                (../protocol-type ='6')) and 
                ((../sport ='eq') or
                (../sport ='neq')))" {
            }
            type union {
                type wellknown-port-tcp;            
                type sport-number-eq-neq-tcp-udp;
            }
        }
        
        leaf sport-number-lt-tcp {
            when "(((../protocol-type ='tcp') or 
                (../protocol-type ='6')) and 
                (../sport ='lt'))" {
            }
            type union {
                type wellknown-port-tcp;            
                type sport-number-lt-tcp-udp;
            }
        }
        
        leaf sport-number-gt-tcp {
            when "(((../protocol-type ='tcp') or
                (../protocol-type ='6')) and 
                (../sport ='gt'))" {
            }
            type union {
                type wellknown-port-tcp;            
                type sport-number-gt-tcp-udp;
            }
        }
        
        leaf sport-number-eq-neq-udp {
            when "(((../protocol-type ='udp')
                or (../protocol-type ='17')) 
                and ((../sport ='eq') or 
                (../sport ='neq')))" {
            }
            type union {
                type wellknown-port-udp;
                type sport-number-eq-neq-tcp-udp;
            }
        }
        
        leaf sport-number-lt-udp {
            when "(((../protocol-type ='udp') 
                or (../protocol-type ='17')) 
                and (../sport ='lt'))" {
            }
            type union {
                type wellknown-port-udp;
                type sport-number-lt-tcp-udp;
            }
        }
        
        leaf sport-number-gt-udp {
            when "(((../protocol-type ='udp') 
                or (../protocol-type ='17')) 
                and (../sport ='gt'))" {
            }
            type union {
                type wellknown-port-udp;
                type sport-number-gt-tcp-udp;
            }
        }

        leaf sport-number-range-lower-tcp {
            when "(((../protocol-type ='tcp') 
                or (../protocol-type ='6')) 
                and (../sport ='range'))" {
            }
            type union {    
                type wellknown-port-tcp;
                type sport-range-lower-tcp-udp;
            }
        }
    
        leaf sport-number-range-lower-udp {
            when "(((../protocol-type ='udp') 
                or (../protocol-type ='17')) 
                and (../sport ='range'))" {
            }
            type union {
                type wellknown-port-udp;                            
                type sport-range-lower-tcp-udp;
            }
        }
       
        leaf sport-number-range-higher-tcp {
            when "(((../protocol-type ='tcp') 
                or (../protocol-type ='6')) 
                and (../sport ='range') 
                and (../sport-number-range-lower-tcp))" {
            }
            type union {            
                type wellknown-port-tcp;
                type sport-range-higher-tcp-udp;
            }
        }

        leaf sport-number-range-higher-udp {
            when "(((../protocol-type ='udp') 
                or (../protocol-type ='17')) 
                and (../sport ='range') 
                and (../sport-number-range-lower-udp))" {
            }
            type union {
                type wellknown-port-udp;
                type sport-range-higher-tcp-udp;
            }
        }
        
        leaf dst-host-any-dip {
            type union {
                type enumeration {
                    enum any {
                        value 1;
                    }
                    enum host {
                        value 2;
                    }
                }
                type dip;
                type dip-cidr;
            }
            mandatory true;
        }
    
        leaf dst-host-ip {
            when "../dst-host-any-dip ='host'" {
            }
            type dip;
        }

        leaf dst-mask {
            when "((../dst-host-any-dip !='any') 
                and (../dst-host-any-dip !='host') 
                and ((not(contains((../dst-host-any-dip),'/')))))" {
            }
            type dip-mask;
        }


        leaf dport {
            when "((../protocol-type ='tcp') 
                or (../protocol-type ='17')
                or (../protocol-type ='udp') 
                or (../protocol-type ='6'))" {
            }

            type enumeration {
                enum eq {
                    value 1;
                }
                enum gt {
                    value 2;
                }               
                enum lt {
                    value 3;
                }                
                enum neq {
                    value 4;
                }              
                enum range {
                    value 5;
                }    
            }
        }
        
        leaf dport-number-eq-neq-tcp {
            when "(((../protocol-type ='tcp') 
                or (../protocol-type ='6')) 
                and ((../dport ='eq') 
                or (../dport ='neq')))" {
            }
            type union {
                type wellknown-port-tcp;            
                type dport-number-eq-neq-tcp-udp;
            }
        }
    
        leaf dport-number-lt-tcp {
            when "(((../protocol-type ='tcp') 
                or (../protocol-type ='6')) 
                and (../dport ='lt'))" {
            }
            type union {
                type wellknown-port-tcp;            
                type dport-number-lt-tcp-udp;
            }
        }
        
        leaf dport-number-gt-tcp {
            when "(((../protocol-type ='tcp') 
                or (../protocol-type ='6')) 
                and (../dport ='gt'))" {
            }
            type union {
                type wellknown-port-tcp;            
                type dport-number-gt-tcp-udp;
            }
        }
        
        leaf dport-number-eq-neq-udp {
            when "(((../protocol-type ='udp') 
                or (../protocol-type ='17')) 
                and ((../dport ='eq') 
                or (../dport ='neq')))" {
            }
            type union {
                type wellknown-port-udp;
                type dport-number-eq-neq-tcp-udp;
            }
        }
        
        leaf dport-number-lt-udp {
            when "(((../protocol-type ='udp') 
                or (../protocol-type ='17')) 
                and (../dport ='lt'))" {
            }
            type union {
                type wellknown-port-udp;
                type dport-number-lt-tcp-udp;
            }
        }

        leaf dport-number-gt-udp {
            when "(((../protocol-type ='udp') 
                or (../protocol-type ='17')) 
                and (../dport ='gt'))" {
            }
            type union {
                type wellknown-port-udp;
                type dport-number-gt-tcp-udp;
            }
        }

        leaf dport-number-range-lower-tcp {
            when "(((../protocol-type ='tcp')
                or (../protocol-type ='6'))
                and ((../dport ='range')))" {
            }
            type union {    
                type wellknown-port-tcp;
                type dport-range-lower-tcp-udp;
            }
        }

        leaf dport-number-range-lower-udp {
            when "(((../protocol-type ='udp') 
                or (../protocol-type ='17')) 
                and ((../dport ='range')))" {
            }
            type union {
                type wellknown-port-udp;
                type dport-range-lower-tcp-udp;
            }
        }
            
        leaf dport-number-range-higher-tcp {
            when "(((../protocol-type ='tcp') or 
                (../protocol-type ='6')) and 
                (../dport ='range') and 
                (../dport-number-range-lower-tcp))" {
            }
            type union {
                type wellknown-port-tcp;
                type dport-range-higher-tcp-udp;
            }
        }

        leaf dport-number-range-higher-udp {
            when "(((../protocol-type ='udp') or 
                (../protocol-type ='17')) and 
                (../dport ='range') and 
                (../dport-number-range-lower-udp))" {
            }    
            type union {
                type wellknown-port-udp;
                type dport-range-lower-tcp-udp;
            }
        }

        leaf dscp {
            type union {
                type wellknown-dscp;
                type dscp-uint;
            }
        }

        leaf urg {
            when "(../protocol-type ='tcp') or 
                (../protocol-type ='6')" {
            }
            type empty;
        }
        leaf ack {
            when "(../protocol-type ='tcp') or
                (../protocol-type ='6')" {
            }
            type empty;
        }

        leaf push {
            when "(../protocol-type ='tcp') or
                (../protocol-type ='6')" {
            }
            type empty;
        }

        leaf fin {
            when "(../protocol-type ='tcp') or 
                (../protocol-type ='6')" {
            }
            type empty;
        }


        leaf rst {
            when "(../protocol-type ='tcp') or
                (../protocol-type ='6')" {
            }
            type empty;
        }
        
        leaf sync {
            when "(../protocol-type ='tcp') or
                (../protocol-type ='6')" {
            }
            type empty;
        }

        leaf vlan {
            //tailf:alt-name vlan;
            description "Vlan";
            type interface:vlan-type;
        }
        
        leaf count {
            type empty;
        }

        leaf log {
            type empty;
        }

    }

    grouping ip-std-access-list-rule {
        leaf action {
            type enumeration {
                enum permit {
                    value 1;
                }
                enum deny {
                    value 2;
                }
                enum hard-drop {
                    value 3;
                }
            }
        }
        
        leaf src-host-any-sip {
            type union {
                type enumeration {
                    enum any {
                        value 1;
                    }
                    enum host {
                        value 2;
                    }

                }
                type sip;
                type sip-cidr;
            }
            mandatory true;
        }

        leaf src-host-ip {
            when "../src-host-any-sip ='host'" {
            }
            type sip;
        }

        leaf src-mask {
            when "((../src-host-any-sip !='any') and
                (../src-host-any-sip !='host') and
                ((not(contains((../src-host-any-sip),'/')))))" {
            }
            type sip-mask;
        }
/*
        leaf vlan {
            //tailf:alt-name vlan;
            description "Vlan";
            type interface:vlan-type;
        }
*/		

        leaf count  {
            type empty;
        }


        leaf log {
            type empty;
        }
        
    }


    grouping l3_access_list_cmds {
        container access-list {
            //tailf:cli-suppress-show-conf-path;
            //standard ACL
            list standard{
                key name;
                leaf name{
                    type l3-acl-policy-name;
                }
                container hide-ip-acl-std {
	                list seq{
	                    key seq-id;
	                    leaf seq-id {
	                        type seq-id-std-ext;
	                    }
	                    uses ip-std-access-list-rule;
	                }
                }
            }
            //extended ACL
            list extended{
                key name;
                leaf name{
                    type l3-acl-policy-name;
                }
                
                container hide-ip-acl-ext {
	                list seq{
	                    key seq-id;
	                    leaf seq-id {
	                        type seq-id-std-ext;
	                    }
	                    uses ip-ext-access-list-rule;
	                }
                }
                
            } //list extended
        } // container access-list
    }// grouping ip

    grouping l3_access_group {
        list access-group {
            //tailf:callpoint IpaclAccessgroupIntTeCP;

            key "ip-access-list ip-direction";

            leaf ip-access-list {
                type l3-acl-policy-name;
            }

            leaf ip-direction {
                type enumeration {
                    enum in {
                        value 1;
                    }
                    enum out {
                        value 2;
                    }
                }
            }

            leaf traffic-type {
                type enumeration {
                    enum switched {
                        value 2;
                    }
                    enum routed {
                        value 3;
                    }
                }
            }
        }
    }

    container ip-acl {
        container ip {
            uses l3_access_list_cmds;
        }
    }


    augment "/interface:interface/interface:tengigabitethernet" {
        container ip-acl-interface {
            container ip {
                uses l3_access_group;
            }
        }
    }
    
    augment "/interface:interface/interface:gigabitethernet" {
        container ip-acl-interface {
            container ip {
                uses l3_access_group;
            }
        }
    }
    
    augment "/interface:interface/interface:fortygigabitethernet" {
        container ip-acl-interface {
            container ip {
                uses l3_access_group;
            }
        }
    }
    augment "/interface:interface/interface:hundredgigabitethernet" {
        container ip-acl-interface {
            container ip {
                uses l3_access_group;
            }
        }
    }
    

    
    augment "/interface:interface/interface:port-channel" {
        container ip-acl-interface {
            container ip {
                uses l3_access_group;
            }
        }
    }

    augment "/rbridge:rbridge-id/interface:interface/interface:ve" {
        container ip-acl-interface {
            container ip {
                uses l3_access_group;
            }
        }
    }

    /*augment "/interface:interface-vlan/interface:interface/interface:ve" {
        container ip-acl-interface {
            container ip {
                uses l3_access_group;
            }
        }
    }*/

	augment "/interface:interface/interface:management/interface:ip" {
        container access-group {

            leaf mgmt-ip-access-list {
                type l3-acl-policy-name;
            }

            leaf mgmt-ip-direction {
                type enumeration {
                    enum in {
                        value 1;
                    }
                }
            }
        }
	}
}
