module vyatta-multicast {
	namespace "urn:vyatta.com:mgmt:vyatta-multicast";
	prefix multicast;

	import vyatta-protocols {
		prefix protocols;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}
	import vyatta-interfaces-vti {
		prefix interfaces-vti;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /protocols:protocols {
		container multicast {
			presence "true";
			configd:priority "299";
			configd:help "Multicast";
			configd:validate "/opt/vyatta/share/tmplscripts/protocols/multicast/configd_validate1.cli";
			container ip {
				presence "true";
				configd:help "Internet Protocol (IP)";
				configd:create "/opt/vyatta/share/tmplscripts/protocols/multicast/ip/configd_create1.cli";
				leaf routing {
					type empty;
					configd:help "Turn on IP Multicast Routing";
					configd:create "/opt/vyatta/share/tmplscripts/protocols/multicast/ip/routing/configd_create.sh";
					configd:delete "/opt/vyatta/share/tmplscripts/protocols/multicast/ip/routing/configd_delete.sh";
				}
				leaf route-limit {
					type uint32 {
						range 1..2147483647 {
							error-message "Must be between 1-2147483647";
						}
					}
					configd:help "Limit number of multicast routes";
					configd:update "/opt/vyatta/share/tmplscripts/protocols/multicast/ip/route-limit/configd_update.sh";
					configd:delete "/opt/vyatta/share/tmplscripts/protocols/multicast/ip/route-limit/configd_delete.sh";
				}
				leaf log-warning {
					type uint32 {
						range 1..2147483647 {
							error-message "Must be between 1-2147483647";
						}
					}
					configd:help "Threshold at which to generate a warning message";
					configd:update "/opt/vyatta/share/tmplscripts/protocols/multicast/ip/log-warning/configd_update.sh";
					configd:delete "/opt/vyatta/share/tmplscripts/protocols/multicast/ip/log-warning/configd_delete.sh";
					configd:validate "/opt/vyatta/share/tmplscripts/protocols/multicast/ip/log-warning/configd_validate1.cli";
				}
			}
			container ipv6 {
				presence "true";
				configd:help "Internet Protocol Version 6 (IPv6)";
				configd:create "/opt/vyatta/share/tmplscripts/protocols/multicast/ipv6/configd_create1.cli";
				leaf routing {
					type empty;
					configd:help "Turn on IPv6 Multicast Routing";
					configd:create "/opt/vyatta/share/tmplscripts/protocols/multicast/ipv6/routing/configd_create.sh";
					configd:delete "/opt/vyatta/share/tmplscripts/protocols/multicast/ipv6/routing/configd_delete.sh";
				}
				leaf route-limit {
					type uint32 {
						range 1..2147483647 {
							error-message "Must be between 1-2147483647";
						}
					}
					configd:help "Limit number of multicast routes";
					configd:update "/opt/vyatta/share/tmplscripts/protocols/multicast/ipv6/route-limit/configd_update.sh";
					configd:delete "/opt/vyatta/share/tmplscripts/protocols/multicast/ipv6/route-limit/configd_delete.sh";
				}
				leaf log-warning {
					type uint32 {
						range 1..2147483647 {
							error-message "Must be between 1-2147483647";
						}
					}
					configd:help "Threshold at which to generate a warning message";
					configd:update "/opt/vyatta/share/tmplscripts/protocols/multicast/ipv6/log-warning/configd_update.sh";
					configd:delete "/opt/vyatta/share/tmplscripts/protocols/multicast/ipv6/log-warning/configd_delete.sh";
					configd:validate "/opt/vyatta/share/tmplscripts/protocols/multicast/ipv6/log-warning/configd_validate1.cli";
				}
			}
		}
	}
	augment /if:interfaces/interfaces-bridge:bridge/interfaces-bridge:ip {
		container multicast {
			configd:help "Multicast";
			configd:validate "/opt/vyatta/share/tmplscripts/interfaces/bridge/ip/multicast/configd_validate1.cli";
			leaf ttl-threshold {
				type uint32 {
					range 1..255 {
						error-message "Must be between 1-255";
					}
				}
				configd:help "Time to live (TTL) threshold";
				configd:update "/opt/vyatta/share/tmplscripts/interfaces/bridge/ip/multicast/ttl-threshold/configd_update.sh";
				configd:delete "/opt/vyatta/share/tmplscripts/interfaces/bridge/ip/multicast/ttl-threshold/configd_delete.sh";
			}
		}
	}
	augment /if:interfaces/interfaces-dataplane:dataplane/interfaces-dataplane:ip {
		container multicast {
			configd:help "Multicast";
			configd:validate "/opt/vyatta/share/tmplscripts/interfaces/dataplane/ip/multicast/configd_validate1.cli";
			leaf ttl-threshold {
				type uint32 {
					range 1..255 {
						error-message "Must be between 1-255";
					}
				}
				configd:help "Time to live (TTL) threshold";
				configd:update "/opt/vyatta/share/tmplscripts/interfaces/dataplane/ip/multicast/ttl-threshold/configd_update.sh";
				configd:delete "/opt/vyatta/share/tmplscripts/interfaces/dataplane/ip/multicast/ttl-threshold/configd_delete.sh";
			}
		}
	}
	augment /if:interfaces/interfaces-dataplane:dataplane/interfaces-dataplane:vif/interfaces-dataplane:ip {
		container multicast {
			configd:help "Multicast";
			configd:validate "/opt/vyatta/share/tmplscripts/interfaces/dataplane/vif/ip/multicast/configd_validate1.cli";
			leaf ttl-threshold {
				type uint32 {
					range 1..255 {
						error-message "Must be between 1-255";
					}
				}
				configd:help "Time to live (TTL) threshold";
				configd:update "/opt/vyatta/share/tmplscripts/interfaces/dataplane/vif/ip/multicast/ttl-threshold/configd_update.sh";
				configd:delete "/opt/vyatta/share/tmplscripts/interfaces/dataplane/vif/ip/multicast/ttl-threshold/configd_delete.sh";
			}
		}
	}
	augment /if:interfaces/interfaces-l2tpeth:l2tpeth/interfaces-l2tpeth:ip {
		container multicast {
			configd:help "Multicast";
			configd:validate "/opt/vyatta/share/tmplscripts/interfaces/l2tpeth/ip/multicast/configd_validate1.cli";
			leaf ttl-threshold {
				type uint32 {
					range 1..255 {
						error-message "Must be between 1-255";
					}
				}
				configd:help "Time to live (TTL) threshold";
				configd:update "/opt/vyatta/share/tmplscripts/interfaces/l2tpeth/ip/multicast/ttl-threshold/configd_update.sh";
				configd:delete "/opt/vyatta/share/tmplscripts/interfaces/l2tpeth/ip/multicast/ttl-threshold/configd_delete.sh";
			}
		}
	}
	augment /if:interfaces/interfaces-l2tpeth:l2tpeth/interfaces-l2tpeth:vif/interfaces-l2tpeth:ip {
		container multicast {
			configd:help "Multicast";
			configd:validate "/opt/vyatta/share/tmplscripts/interfaces/l2tpeth/vif/ip/multicast/configd_validate1.cli";
			leaf ttl-threshold {
				type uint32 {
					range 1..255 {
						error-message "Must be between 1-255";
					}
				}
				configd:help "Time to live (TTL) threshold";
				configd:update "/opt/vyatta/share/tmplscripts/interfaces/l2tpeth/vif/ip/multicast/ttl-threshold/configd_update.sh";
				configd:delete "/opt/vyatta/share/tmplscripts/interfaces/l2tpeth/vif/ip/multicast/ttl-threshold/configd_delete.sh";
			}
		}
	}
	augment /if:interfaces/interfaces-loopback:loopback/interfaces-loopback:ip {
		container multicast {
			configd:help "Multicast";
			configd:validate "/opt/vyatta/share/tmplscripts/interfaces/loopback/ip/multicast/configd_validate1.cli";
			leaf ttl-threshold {
				type uint32 {
					range 1..255 {
						error-message "Must be between 1-255";
					}
				}
				configd:help "Time to live (TTL) threshold";
				configd:update "/opt/vyatta/share/tmplscripts/interfaces/loopback/ip/multicast/ttl-threshold/configd_update.sh";
				configd:delete "/opt/vyatta/share/tmplscripts/interfaces/loopback/ip/multicast/ttl-threshold/configd_delete.sh";
			}
		}
	}
	augment /if:interfaces/interfaces-openvpn:openvpn/interfaces-openvpn:ip {
		container multicast {
			configd:help "Multicast";
			configd:validate "/opt/vyatta/share/tmplscripts/interfaces/openvpn/ip/multicast/configd_validate1.cli";
			leaf ttl-threshold {
				type uint32 {
					range 1..255 {
						error-message "Must be between 1-255";
					}
				}
				configd:help "Time to live (TTL) threshold";
				configd:update "/opt/vyatta/share/tmplscripts/interfaces/openvpn/ip/multicast/ttl-threshold/configd_update.sh";
				configd:delete "/opt/vyatta/share/tmplscripts/interfaces/openvpn/ip/multicast/ttl-threshold/configd_delete.sh";
			}
		}
	}
	augment /if:interfaces/interfaces-tunnel:tunnel/interfaces-tunnel:ip {
		container multicast {
			configd:help "Multicast";
			configd:validate "/opt/vyatta/share/tmplscripts/interfaces/tunnel/ip/multicast/configd_validate1.cli";
			leaf ttl-threshold {
				type uint32 {
					range 1..255 {
						error-message "Must be between 1-255";
					}
				}
				configd:help "Time to live (TTL) threshold";
				configd:update "/opt/vyatta/share/tmplscripts/interfaces/tunnel/ip/multicast/ttl-threshold/configd_update.sh";
				configd:delete "/opt/vyatta/share/tmplscripts/interfaces/tunnel/ip/multicast/ttl-threshold/configd_delete.sh";
			}
		}
	}
	augment /if:interfaces/interfaces-vti:vti/interfaces-vti:ip {
		container multicast {
			configd:help "Multicast";
			configd:validate "/opt/vyatta/share/tmplscripts/interfaces/vti/ip/multicast/configd_validate1.cli";
			leaf ttl-threshold {
				type uint32 {
					range 1..255 {
						error-message "Must be between 1-255";
					}
				}
				configd:help "Time to live (TTL) threshold";
				configd:update "/opt/vyatta/share/tmplscripts/interfaces/vti/ip/multicast/ttl-threshold/configd_update.sh";
				configd:delete "/opt/vyatta/share/tmplscripts/interfaces/vti/ip/multicast/ttl-threshold/configd_delete.sh";
			}
		}
	}
}
