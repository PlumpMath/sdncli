/******************************************************************
* FOS EM CLI Yang model that will contain linecard managemet  clis 
*
*  September 2011-2012, Hung Nguyen
*
* Copyright (c) 2010 by Brocade Communications Systems, Inc.
* All rights reserved.
*******************************************************************/

module brocade-linecard-management {
    namespace "urn:brocade.com:mgmt:brocade-linecard-management";
    prefix "linecard-management";

    /* Linkage Statements */

    import tailf-common {
        prefix tailf;
    }

    import brocade-common-def {
        prefix common-def;
    }

    import brocade-rbridge {
        prefix rbridge; 
    }

    /* Meta Information */

    organization
        "Brocade Communications Systems, Inc.";

    contact
        "Brocade Communications Systems, Inc.
         Postal: 130 Holger Way
                 San Jose, CA 95134
                  U.S.A
         Tel: +1-408-333-8000
         E-mail: support@Brocade.com
         web: www.brocade.com.";

    description
        "This linecard management module is used to manage linecards.
         It can be used to configure, show, or turn on/off a linecard.n";

    /* Revision history */

    revision "2011-09-06" {
        description
            "Initial version of this management module.";
    }

    /* Module Definition */

    typedef linecardid {
        type string {
            pattern '([1-9]|[1][0-6])' {
                error-message "Invalid slot number. Slot number must be in the range 1..16";
            }
        }
    }

    grouping linecard-cmds {
        container linecard {
   
	    list linecards {
 
                key "linecardName";
                leaf linecardName {
                    type linecardid;
                    mandatory true;
                }
                leaf linecardType {
				    type enumeration {
                        enum LC48X10G {
                            value 1;
                        }
                        enum LC12X40G {
                            value 2;
                        }
                        enum LC72X1G {
                            value 8;
                        }
                        enum LC48X1G {
                            value 9;
                        }
                        enum LC36X10G {
                            value 10;
                        }
                        enum LC6X100G{
                            value 11;
                        }
                        enum LC27X40G {
                            value 12;
                        }
                        enum LC48X10GT{
                            value 13;
                        }
                    }
                }
            }
        }
    }

    augment "/rbridge:rbridge-id" {
        container global-lc-holder {
            uses linecard-cmds;
        }
    }

    typedef slotnum {
        type uint32;
    }

    typedef sfmnum {
        type uint32;
    }   

    typedef partition {
        type enumeration {
            enum p0 {
            }
            enum p1 {
            }
        }
    }

    typedef platform-type {
        type uint32;
    }

    typedef lcslotidtype {
        type string {
            length 2 {
            }
        }
    }

    /* define the "show " functionality */
    augment "/common-def:show" {
       container linecardinfo {
          tailf:action linecard {
             input {
                leaf rbridge-id {
                   type common-def:rbridge-id-type;
                   mandatory false;
                }
             }
             output {}
          }
       }

       container sfminfo {
          tailf:action sfm {
             input {
                leaf rbridge-id {
                   type common-def:rbridge-id-type;
                   mandatory false;
                }
             }
             output {}
          }
        }

       container mminfor {
           tailf:action mm {
              input {
                leaf rbridge-id {
                   type common-def:rbridge-id-type;
                   mandatory false;
                }
             }
              output {}
          }
        }

       container slotsinfor {
           tailf:action slots {
              input {
                leaf rbridge-id {
                   type common-def:rbridge-id-type;
                   mandatory false;
                }
             }
              output {}
          }
        }
    } /* end of show */

    container linecardservice {
        tailf:action power-off {
          input {
              choice blade-type {
              case linecard {
                leaf linecard {
                   type slotnum;
                   mandatory true;
                }
              }
              case sfm {
                leaf sfm {
                   type sfmnum;
                   mandatory true;
                }
              }                   
              }
          }
        }
        tailf:action power-on {
          input {
              choice blade-type {
              case linecard {
                leaf linecard {
                   type slotnum;
                   mandatory true;
                }
              }
              case sfm {
                leaf sfm {
                   type sfmnum;
                   mandatory true;
                }
              }
              }
           }
        }
    }
}
