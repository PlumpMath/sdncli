module vyatta-types {
	namespace "urn:vyatta.com:mgmt:vyatta-types";
	prefix types;

	import ietf-inet-types {
		prefix inet;
	}
	import ietf-yang-types {
		prefix ietf;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-01-07 {
		description "Added hostname-port, ipv4-addr-port and ipv6-addr-port.
			     Added ip-address and ip-prefix.";
	}
	revision 2014-10-28 {
		description "Update for 3.2.1R1";
	}
	revision 2014-08-24 {
		description "Initial revision.";
	}

	typedef ipv4-address {
		type inet:ipv4-address {
			configd:pattern-help "<x.x.x.x>";
			configd:help "IPv4 Address";
		}
	}
	typedef ipv6-address {
		type inet:ipv6-address {
			configd:pattern-help "<h:h:h:h:h:h:h:h>";
			configd:help "IPv6 Address";
		}

	}
	typedef ip-address {
		type union {
			type ipv4-address;
			type ipv6-address;
		}
	}
	typedef ipv4-prefix {
		type string {
			pattern '(([0-9]|[1-9][0-9]|1[0-9][0-9]|2[0-4][0-9]|25[0-5])\.){3}'
				+  '([0-9]|[1-9][0-9]|1[0-9][0-9]|2[0-4][0-9]|25[0-5])'
				+ '/(([0-9])|([1-2][0-9])|(3[0-2]))';
			configd:pattern-help "<x.x.x.x/x>";
			configd:help "IPv4 Prefix";
		}
	}
	typedef ipv6-prefix {
		type string {
			pattern '((:|[0-9a-fA-F]{0,4}):)([0-9a-fA-F]{0,4}:){0,5}'
				+ '((([0-9a-fA-F]{0,4}:)?(:|[0-9a-fA-F]{0,4}))|'
				+ '(((25[0-5]|2[0-4][0-9]|[01]?[0-9]?[0-9])\.){3}'
				+ '(25[0-5]|2[0-4][0-9]|[01]?[0-9]?[0-9])))'
				+ '(/(([0-9])|([0-9]{2})|(1[0-1][0-9])|(12[0-8])))';
			pattern '(([^:]+:){6}(([^:]+:[^:]+)|(.*\..*)))|'
				+ '((([^:]+:)*[^:]+)?::(([^:]+:)*[^:]+)?)'
				+ '(/.+)';
			configd:pattern-help "<h:h:h:h:h:h:h:h/x>";
			configd:help "IPv6 Prefix";
		}
	}
	typedef ip-prefix {
		type union {
			type ipv4-prefix;
			type ipv6-prefix;
		}
	}
	typedef hostname-port {
		type string {
			pattern '([a-z]|[A-Z]){1}'
			      + '([a-z]|[A-Z]|[-_]){0,62}'
			      + '(:[0-9]+){0,5}?';
			configd:pattern-help "<hostname[:port]>";
			configd:help "Remote host name and optional port";
		}
	}
	typedef ipv4-addr-port {
	  type string {
	    pattern '(([0-9]|[1-9][0-9]|1[0-9][0-9]|2[0-4][0-9]|25[0-5])\.){3}'
	          + '([0-9]|[1-9][0-9]|1[0-9][0-9]|2[0-4][0-9]|25[0-5])'
		  + '(:[0-9]+){0,5}?';
	    configd:pattern-help "<x.x.x.x[:port]>";
	    configd:help "IPv4 Address and optional port";
	  }
	}
	typedef ipv6-addr-port {
	  type string {
	    pattern '\[((:|[0-9a-fA-F]{0,4}):)([0-9a-fA-F]{0,4}:){0,5}'
		  + '((([0-9a-fA-F]{0,4}:)?(:|[0-9a-fA-F]{0,4}))|'
		  + '(((25[0-5]|2[0-4][0-9]|[01]?[0-9]?[0-9])\.){3}'
		  + '(25[0-5]|2[0-4][0-9]|[01]?[0-9]?[0-9])))\]'
		  + '(:[0-9]+){0,5}?';
	    configd:pattern-help "<[h:h:h:h:h:h:h:h][:port]>";
	    configd:help "IPv6 Address enclosed in brackets and optional port";
	  }
	}

	typedef mac-address {
		type ietf:mac-address {
			configd:pattern-help "<h:h:h:h:h:h>";
			configd:help "MAC Address";
		}
	}
}
