module vyatta-interfaces {
	namespace "urn:vyatta.com:mgmt:vyatta-interfaces";
	prefix if;

	import configd { prefix configd; }
	import vyatta-types { prefix types; }

	organization "Brocade Communications Systems, Inc.";
	contact
		"Brocade Communications Systems, Inc.
		 Postal: 130 Holger Way
		 	 San Jose, CA 95134
		 E-mail: support@Brocade.com
		 Web: www.brocade.com";
	revision 2014-12-02 {
		description "Add post-processing of interface changes";
	}

	revision 2014-10-28 {
		description "Update for 3.2.1R1";
	}
	
	revision 2014-05-30 {
		description "Initial revision.";
	} 

	typedef address {
		type union {
			type types:ipv4-prefix {
				configd:help "IPv4 Address";
			}
			type types:ipv6-prefix {
				configd:help "IPv6 Address";
			}
			configd:syntax "valid_address $VAR(@)";
		}
	}

	typedef address-dhcp {
		type union {
			type enumeration {
				enum dhcp {
					configd:help "Use DHCP to acquire an address";
				}
				enum dhcpv6  {
					configd:help "Use DHCPv6 to acquire an address";
				}
			}
			type address;
		}
	}

	container interfaces {
		presence "true";
		configd:help "Network interfaces";
		configd:begin "/opt/vyatta/sbin/vyatta-delete-addrs.pl";
		configd:end "/bin/run-parts ${vyatta_datarootdir}/tmplscripts${CONFIGD_PATH}/configd_end.d";
	}
}
