module vyatta-system-mgmt {
	namespace "urn:vyatta.com:mgmt:vyatta-system-mgmt";
	prefix system-mgmt;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /system:system {
		container config-management {
			presence "true";
			configd:help "Configuration management settings";
			container commit-archive {
				presence "true";
				configd:priority "400";
				configd:help "Commit archival settings";
				configd:end "/opt/vyatta/share/tmplscripts/system/config-management/commit-archive/configd_end.sh";
				leaf-list location {
					type string {
						configd:syntax "/opt/vyatta/share/tmplscripts/system/config-management/commit-archive/location/configd_syntax1.cli";
					}
					ordered-by "user";
					configd:help "Commit archive location";
					configd:comp_help "/opt/vyatta/share/tmplscripts/system/config-management/commit-archive/location/configd_comp_help.txt";
				}
			}
			leaf commit-revisions {
				type uint32 {
					range 0..65535 {
						error-message "Commit revisions must be in range 0 to 65535";
					}
				}
				configd:priority "400";
				configd:help "Commit revisions";
				configd:update "/opt/vyatta/share/tmplscripts/system/config-management/commit-revisions/configd_update.sh";
				configd:delete "/opt/vyatta/share/tmplscripts/system/config-management/commit-revisions/configd_delete.sh";
			}
		}
	}
}
