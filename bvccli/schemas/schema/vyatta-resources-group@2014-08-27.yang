module vyatta-resources-group {
	namespace "urn:vyatta.com:mgmt:vyatta-resources-group";
	prefix resources-group;

	import vyatta-resources {
		prefix resources;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /resources:resources {
		container group {
			presence "true";
			configd:priority "300";
			configd:help "Group of addresses, networks and ports";
			list port-group {
				configd:help "Group of ports";
				configd:end "/opt/vyatta/share/tmplscripts/resources/group/port-group/configd_end.sh";
				key "tagnode";
				leaf tagnode {
					type string {
						pattern "[!-~]{1,32}" {
							error-message "Port group name must be 32 characters or less";
						}
						pattern "[0-9A-Za-z][_0-9A-Za-z]*" {
							error-message "only alpha-numeric policy name allowed";
						}
						configd:syntax "/opt/vyatta/share/tmplscripts/resources/group/port-group/configd_syntax1.cli";
					}
					configd:help "Group of ports";
				}
				leaf description {
					type string;
					configd:help "Port-group description";
				}
				leaf-list port {
					type string {
						configd:syntax "/opt/vyatta/share/tmplscripts/resources/group/port-group/port/configd_syntax1.cli";
					}
					ordered-by "user";
					configd:help "Port-group member";
					configd:validate "/opt/vyatta/share/tmplscripts/resources/group/port-group/port/configd_validate1.cli";
				}
			}
			list address-group {
				configd:help "Group of addresses and networks";
				configd:end "/opt/vyatta/share/tmplscripts/resources/group/address-group/configd_end.sh";
				configd:validate "/opt/vyatta/share/tmplscripts/resources/group/address-group/configd_validate1.cli";
				key "tagnode";
				leaf tagnode {
					type string {
						pattern "[!-~]{1,32}" {
							error-message "Firewall group name must be 32 characters or less";
						}
						pattern "[0-9A-Za-z][_0-9A-Za-z]*" {
							error-message "only alpha-numeric policy name allowed";
						}
					}
					configd:help "Group of addresses and networks";
				}
				leaf description {
					type string;
					configd:help "Address-group description";
				}
				leaf-list address {
					type string {
						configd:syntax "/opt/vyatta/share/tmplscripts/resources/group/address-group/address/configd_syntax1.cli";
						configd:syntax "/opt/vyatta/share/tmplscripts/resources/group/address-group/address/configd_syntax2.cli";
						configd:syntax "/opt/vyatta/share/tmplscripts/resources/group/address-group/address/configd_syntax3.cli";
						configd:syntax "/opt/vyatta/share/tmplscripts/resources/group/address-group/address/configd_syntax4.cli";
						configd:syntax "/opt/vyatta/share/tmplscripts/resources/group/address-group/address/configd_syntax5.cli";
					}
					ordered-by "user";
					configd:help "Address-group member";
				}
			}
		}
	}
}
