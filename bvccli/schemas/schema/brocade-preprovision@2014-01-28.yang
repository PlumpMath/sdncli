/***********************************************************************
 * brocade-preprovision.yang: Brocade 'Pre-Provision Configuration'
 *                            module.
 *
 * Feb 2014,  Kuai Yu
 *
 * Copyright (c) 2014 by Brocade Communications Systems, Inc.
 * All rights reserved.
 *
 **********************************************************************/
module brocade-preprovision {
    namespace "urn:brocade.com:mgmt:brocade-preprovision";
    prefix "preprovision";

    import tailf-common {
        prefix tailf;
    }

    import brocade-common-def {
        prefix common-def;
    }

    contact
        "Brocade Communications Systems, Inc.
         Postal: 130 Holger Way
                 San Jose, CA 95134
                  U.S.A
         Tel: +1-408-333-8000
         E-mail: support@Brocade.com
         web: www.brocade.com.";

    description
        "This management module is an instrumentation to manage preprovision
         feature.";

    revision "2014-01-28" {
        description
            "Initial version of the management module brocade-preprovision.";
    }

    container preprovision {
        description "Preprovision profile";

        list rbridge-id {
            key "rbridge-id wwn";
            leaf rbridge-id {
                type common-def:rbridge-id-type;
            }
            leaf wwn {
                type common-def:wwn-type;
                description
                    "This specifies the WWN value for a given rbridge-id 
                    identified by the value of the corresponding instance of 'preprovision/rbridge-id'";
            }
        }
    }


	/* define the "show bare-metal" functionality */
	augment "/common-def:show" {
        container bare-metal {
            tailf:action bare-metal {
                input {}           
                output {
                    leaf bare-metal-state {
                       type string;
                       description
                        "This leaf indicates the bare-metal state on the system.";
                    }
                }
            } /* show bare-metal */
        }
    } /* end of show */



rpc show-bare-metal-state {
    output {
        leaf bare-metal-state {
                   type string;
                   description
                    "This leaf indicates the bare-metal state on the system.";
        }
    }
}

}
