/***********************************************************************
* brocade-entity.yang: Brocade Entity management module.
*
* May 2014, Harish K Sekar
*
* Copyright (c) 2014 by Brocade Communications Systems, Inc.
* All rights reserved.
*
**********************************************************************/
module brocade-entity {
	namespace "urn:brocade.com:mgmt:brocade-entity";
	prefix "entity";

	import tailf-common {
		prefix tailf;
	}

	import brocade-common-def {
		prefix common-def;
	}

	organization
		"Brocade Communications Systems, Inc.";

	contact
		"Brocade Communications Systems, Inc.
		Postal: 130 Holger Way
		San Jose, CA 95134
		U.S.A
		Tel: +1-408-333-8000
		E-mail: support@Brocade.com
		web: www.brocade.com.";

	description
		"This management module is an instrumentation to manage 
		all physical and logical entities in the managed device.";

	reference
		"A. Bierman and K. McCloghrie, 'Entity MIB (Version 3)', 
		RFC 4133, August 2005.";


	revision "2014-05-09" {
		description
			"Initial version of this management module.";
	}

	typedef physical-class-type {
		type enumeration {
			enum other			{ value 1; }
			enum unknown		{ value 2; }
			enum chassis		{ value 3; }
			enum backplane		{ value 4; }
			enum container		{ value 5; }
			enum power-supply 	{ value 6; }
			enum fan			{ value 7; }
			enum sensor			{ value 8; }
			enum module			{ value 9; }
			enum port			{ value 10; }
			enum stack			{ value 11; }
			enum cpu			{ value 12; }
		}
		description
			"An enumerated value which provides an indication of the
			general hardware type of a particular physical entity.
			There are no restrictions as to the number of
			entPhysicalEntries of each entPhysicalClass, which must be 
			instantiated by an agent.

			The enumeration 'other' is applicable if the physical 
			entity class is known, but does not match any of the 
			supported values.

			The enumeration 'unknown' is applicable if the physical
			entity class is unknown to the agent.

			The enumeration 'chassis' is applicable if the physical
			entity class is an overall container for networking
			equipment. Any class of physical entity, except a stack,
			may be contained within a chassis; and a chassis may only
			be contained within a stack.

			The enumeration 'backplane' is applicable if the physical
			entity class is some sort of device for aggregating and
			forwarding networking traffic, such as a shared backplane 
			in a modular ethernet switch. Note that an agent may 
			model a backplane as a single physical entity, which is 
			actually implemented as multiple discrete physical 
			components (within a chassis or stack).

			The enumeration 'container' is applicable if the physical
			entity class is capable of containing one or more removable
			physical entities, possibly of different types. For
			example, each (empty or full) slot in a chassis will be
			modeled as a container. Note that all removable physical
			entities should be modeled within a container entity, such
			as field-replaceable modules, fans, or power supplies. Note
			that all known containers should be modeled by the agent,
			including empty containers.

			The enumeration 'power-supply' is applicable if the physical
			entity class is a power-supplying component.

			The enumeration 'fan' is applicable if the physical entity
			class is a fan or other heat-reduction component.

			The enumeration 'sensor' is applicable if the physical
			entity class is some sort of sensor, such as a temperature
			sensor within a router chassis.

			The enumeration 'module' is applicable if the physical
			entity class is some sort of self-contained sub-system. If
			the enumeration 'module' is removable, then it should be
			modeled within a container entity, otherwise it should be
			modeled directly within another physical entity (e.g., a
			chassis or another module).

			The enumeration 'port' is applicable if the physical entity
			class is some sort of networking port, capable of receiving
			and/or transmitting networking traffic.

			The enumeration 'stack' is applicable if the physical 
			entity class is some sort of super-container 
			(possibly virtual), intended to group together multiple 
			chassis entities. A stack may be realized by a 'virtual'
			cable, a real interconnect cable, attached to multiple 
			chassis, or may in fact be comprised of multiple 
			interconnect cables. A stack should not be modeled within 
			any other physical entities, but a stack may be contained 
			within another stack. Only chassis entities should be 
			contained within a stack.

			The enumeration 'cpu' is applicable if the physical entity
			class is some sort of central processing unit.";
	}

	typedef physical-index-type {
		type int32 {
			range "1..2147483647";
		}
		description
			"An arbitrary value that uniquely identifies the physical
			entity. The value should be a small, positive integer.
			Index values for different physical entities are not
			necessarily contiguous.";
	}

	rpc get-contained-in-ID {
		description 
			"This is a function that returns the slot/container 
			name/ID, where this managed device is 'contained in'. 
			The managed device here, is typically 1 Rack Unit (RU) 
			device.";

		output {
			leaf contained-in-ID {
			type common-def:name-string64;
			description
				"This represents the textual name/ID of the 
				slot/container that 'contains' this managed 
				device.";
			}
		}
	}
} /* end of module brocade-entity.yang */
