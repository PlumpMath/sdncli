module vyatta-protocols-igmp {
	namespace "urn:vyatta.com:mgmt:vyatta-protocols-igmp";
	prefix protocols-igmp;

	import vyatta-types {
		prefix types;
	}
	import vyatta-protocols {
		prefix protocols;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}
	import vyatta-interfaces-vti {
		prefix interfaces-vti;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /protocols:protocols {
		container igmp {
			presence "true";
			configd:priority "760";
			configd:help "Internet Group Management Protocol (IGMP)";
			configd:validate "/opt/vyatta/share/tmplscripts/protocols/igmp/configd_validate1.cli";
			leaf limit-exception {
				type uint32 {
					configd:syntax "/opt/vyatta/share/tmplscripts/protocols/igmp/limit-exception/configd_syntax1.cli";
				}
				configd:help "Specify access-list that defines multicast groups that are exempted from being subject to configured limit";
				configd:allowed "/opt/vyatta/share/tmplscripts/protocols/igmp/limit-exception/configd_allowed.sh";
				configd:update "/opt/vyatta/share/tmplscripts/protocols/igmp/limit-exception/configd_update.sh";
				configd:delete "/opt/vyatta/share/tmplscripts/protocols/igmp/limit-exception/configd_delete.sh";
				configd:validate "/opt/vyatta/share/tmplscripts/protocols/igmp/limit-exception/configd_validate1.cli";
				configd:validate "/opt/vyatta/share/tmplscripts/protocols/igmp/limit-exception/configd_validate2.cli";
			}
			leaf limit {
				type uint32 {
					range 1..2097152 {
						error-message "Must be between 1-2097152";
					}
				}
				configd:help "Configure the limit on the maximum number of group membership states";
				configd:update "/opt/vyatta/share/tmplscripts/protocols/igmp/limit/configd_update.sh";
				configd:delete "/opt/vyatta/share/tmplscripts/protocols/igmp/limit/configd_delete.sh";
			}
			container ssm-map {
				presence "true";
				configd:help "Enable SSM mapping on the router";
				configd:create "/opt/vyatta/share/tmplscripts/protocols/igmp/ssm-map/configd_create.sh";
				configd:delete "/opt/vyatta/share/tmplscripts/protocols/igmp/ssm-map/configd_delete.sh";
				container static {
					presence "true";
					configd:help "Configure the static mode of defining SSM mapping";
					configd:validate "/opt/vyatta/share/tmplscripts/protocols/igmp/ssm-map/static/configd_validate1.cli";
					list access-list {
						configd:help "Configure access-list for the static mode of defining SSM mapping";
						configd:allowed "/opt/vyatta/share/tmplscripts/protocols/igmp/ssm-map/static/access-list/configd_allowed.sh";
						configd:validate "/opt/vyatta/share/tmplscripts/protocols/igmp/ssm-map/static/access-list/configd_validate1.cli";
						configd:validate "/opt/vyatta/share/tmplscripts/protocols/igmp/ssm-map/static/access-list/configd_validate2.cli";
						key "tagnode";
						leaf tagnode {
							type uint32 {
								configd:syntax "/opt/vyatta/share/tmplscripts/protocols/igmp/ssm-map/static/access-list/configd_syntax1.cli";
							}
							configd:help "Configure access-list for the static mode of defining SSM mapping";
							configd:allowed "/opt/vyatta/share/tmplscripts/protocols/igmp/ssm-map/static/access-list/configd_allowed.sh";
						}
						leaf-list source {
							type types:ipv4-address;
							ordered-by "user";
							configd:help "Configure source address to use for static map group";
							configd:create "/opt/vyatta/share/tmplscripts/protocols/igmp/ssm-map/static/access-list/source/configd_create.sh";
							configd:delete "/opt/vyatta/share/tmplscripts/protocols/igmp/ssm-map/static/access-list/source/configd_delete.sh";
						}
					}
				}
			}
		}
	}
	augment /if:interfaces/interfaces-bridge:bridge/interfaces-bridge:ip {
		container igmp {
			presence "true";
			configd:help "Internet Group Management Protocol (IGMP)";
			configd:priority "462";
			configd:end "/opt/vyatta/share/tmplscripts/interfaces/bridge/ip/igmp/configd_end.sh";
			configd:validate "/opt/vyatta/share/tmplscripts/interfaces/bridge/ip/igmp/configd_validate1.cli";
			configd:validate "/opt/vyatta/share/tmplscripts/interfaces/bridge/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/bridge/ip/igmp/querier/querier-timeout/configd_update.sh";
					configd:delete "/opt/vyatta/share/tmplscripts/interfaces/bridge/ip/igmp/querier/querier-timeout/configd_delete.sh";
				}
			}
			leaf offlink {
				type empty;
				configd:help "Enable off-link for IGMP";
				configd:create "/opt/vyatta/share/tmplscripts/interfaces/bridge/ip/igmp/offlink/configd_create.sh";
				configd:delete "/opt/vyatta/share/tmplscripts/interfaces/bridge/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/bridge/ip/igmp/startup-query-interval/configd_update.sh";
				configd:delete "/opt/vyatta/share/tmplscripts/interfaces/bridge/ip/igmp/startup-query-interval/configd_delete.sh";
			}
			container immediate-leave {
				presence "true";
				configd:help "Immediate leave feature";
				configd:validate "/opt/vyatta/share/tmplscripts/interfaces/bridge/ip/igmp/immediate-leave/configd_validate1.cli";
				leaf group-list {
					type uint32 {
						configd:syntax "/opt/vyatta/share/tmplscripts/interfaces/bridge/ip/igmp/immediate-leave/group-list/configd_syntax1.cli";
					}
					configd:help "Defines multicast groups in which the immediate leave feature is enabled";
					configd:allowed "/opt/vyatta/share/tmplscripts/interfaces/bridge/ip/igmp/immediate-leave/group-list/configd_allowed.sh";
					configd:update "/opt/vyatta/share/tmplscripts/interfaces/bridge/ip/igmp/immediate-leave/group-list/configd_update.sh";
					configd:delete "/opt/vyatta/share/tmplscripts/interfaces/bridge/ip/igmp/immediate-leave/group-list/configd_delete.sh";
					configd:validate "/opt/vyatta/share/tmplscripts/interfaces/bridge/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/bridge/ip/igmp/robustness-variable/configd_update.sh";
				configd:delete "/opt/vyatta/share/tmplscripts/interfaces/bridge/ip/igmp/robustness-variable/configd_delete.sh";
			}
			leaf limit-exception {
				type uint32 {
					configd:syntax "/opt/vyatta/share/tmplscripts/interfaces/bridge/ip/igmp/limit-exception/configd_syntax1.cli";
				}
				configd:help "Specify access-list that defines multicast groups that are exempted from being subject to configured limit";
				configd:allowed "/opt/vyatta/share/tmplscripts/interfaces/bridge/ip/igmp/limit-exception/configd_allowed.sh";
				configd:update "/opt/vyatta/share/tmplscripts/interfaces/bridge/ip/igmp/limit-exception/configd_update.sh";
				configd:delete "/opt/vyatta/share/tmplscripts/interfaces/bridge/ip/igmp/limit-exception/configd_delete.sh";
				configd:validate "/opt/vyatta/share/tmplscripts/interfaces/bridge/ip/igmp/limit-exception/configd_validate1.cli";
				configd:validate "/opt/vyatta/share/tmplscripts/interfaces/bridge/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/bridge/ip/igmp/limit/configd_update.sh";
				configd:delete "/opt/vyatta/share/tmplscripts/interfaces/bridge/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/bridge/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/bridge/ip/igmp/last-member-query-count/configd_update.sh";
				configd:delete "/opt/vyatta/share/tmplscripts/interfaces/bridge/ip/igmp/last-member-query-count/configd_delete.sh";
			}
			list static-group {
				configd:priority "780";
				configd:help "Set standard IP Multicast group address to be configured as a static group member";
				configd:create "/opt/vyatta/share/tmplscripts/interfaces/bridge/ip/igmp/static-group/configd_create.sh";
				configd:end "/opt/vyatta/share/tmplscripts/interfaces/bridge/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/bridge/ip/igmp/static-group/source/configd_syntax1.cli";
					}
					ordered-by "user";
					configd:help "Configure standard IP source address as a static source from where multicast packets originate";
					configd:allowed "/opt/vyatta/share/tmplscripts/interfaces/bridge/ip/igmp/static-group/source/configd_allowed.sh";
					configd:create "/opt/vyatta/share/tmplscripts/interfaces/bridge/ip/igmp/static-group/source/configd_create.sh";
					configd:delete "/opt/vyatta/share/tmplscripts/interfaces/bridge/ip/igmp/static-group/source/configd_delete.sh";
				}
			}
			list join-group {
				configd:help "Configure a join multicast group";
				configd:delete "/opt/vyatta/share/tmplscripts/interfaces/bridge/ip/igmp/join-group/configd_delete.sh";
				configd:end "/opt/vyatta/share/tmplscripts/interfaces/bridge/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/bridge/ip/igmp/last-member-query-interval/configd_update.sh";
				configd:delete "/opt/vyatta/share/tmplscripts/interfaces/bridge/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/bridge/ip/igmp/version/configd_update.sh";
				configd:delete "/opt/vyatta/share/tmplscripts/interfaces/bridge/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/bridge/ip/igmp/access-group/configd_allowed.sh";
				configd:update "/opt/vyatta/share/tmplscripts/interfaces/bridge/ip/igmp/access-group/configd_update.sh";
				configd:delete "/opt/vyatta/share/tmplscripts/interfaces/bridge/ip/igmp/access-group/configd_delete.sh";
				configd:validate "/opt/vyatta/share/tmplscripts/interfaces/bridge/ip/igmp/access-group/configd_validate1.cli";
			}
			leaf enforce-router-alert {
				type empty;
				configd:help "Enable strict RA (Router Advertisement) validation for IGMP";
				configd:create "/opt/vyatta/share/tmplscripts/interfaces/bridge/ip/igmp/enforce-router-alert/configd_create.sh";
				configd:delete "/opt/vyatta/share/tmplscripts/interfaces/bridge/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/bridge/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/bridge/ip/igmp/startup-query-count/configd_update.sh";
				configd:delete "/opt/vyatta/share/tmplscripts/interfaces/bridge/ip/igmp/startup-query-count/configd_delete.sh";
			}
		}
	}
	augment /if:interfaces/interfaces-dataplane:dataplane/interfaces-dataplane:ip {
		container igmp {
			presence "true";
			configd:help "Internet Group Management Protocol (IGMP)";
			configd:priority "462";
			configd:end "/opt/vyatta/share/tmplscripts/interfaces/dataplane/ip/igmp/configd_end.sh";
			configd:validate "/opt/vyatta/share/tmplscripts/interfaces/dataplane/ip/igmp/configd_validate1.cli";
			configd:validate "/opt/vyatta/share/tmplscripts/interfaces/dataplane/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/dataplane/ip/igmp/querier/querier-timeout/configd_update.sh";
					configd:delete "/opt/vyatta/share/tmplscripts/interfaces/dataplane/ip/igmp/querier/querier-timeout/configd_delete.sh";
				}
			}
			leaf offlink {
				type empty;
				configd:help "Enable off-link for IGMP";
				configd:create "/opt/vyatta/share/tmplscripts/interfaces/dataplane/ip/igmp/offlink/configd_create.sh";
				configd:delete "/opt/vyatta/share/tmplscripts/interfaces/dataplane/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/dataplane/ip/igmp/startup-query-interval/configd_update.sh";
				configd:delete "/opt/vyatta/share/tmplscripts/interfaces/dataplane/ip/igmp/startup-query-interval/configd_delete.sh";
			}
			container immediate-leave {
				presence "true";
				configd:help "Immediate leave feature";
				configd:validate "/opt/vyatta/share/tmplscripts/interfaces/dataplane/ip/igmp/immediate-leave/configd_validate1.cli";
				leaf group-list {
					type uint32 {
						configd:syntax "/opt/vyatta/share/tmplscripts/interfaces/dataplane/ip/igmp/immediate-leave/group-list/configd_syntax1.cli";
					}
					configd:help "Defines multicast groups in which the immediate leave feature is enabled";
					configd:allowed "/opt/vyatta/share/tmplscripts/interfaces/dataplane/ip/igmp/immediate-leave/group-list/configd_allowed.sh";
					configd:update "/opt/vyatta/share/tmplscripts/interfaces/dataplane/ip/igmp/immediate-leave/group-list/configd_update.sh";
					configd:delete "/opt/vyatta/share/tmplscripts/interfaces/dataplane/ip/igmp/immediate-leave/group-list/configd_delete.sh";
					configd:validate "/opt/vyatta/share/tmplscripts/interfaces/dataplane/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/dataplane/ip/igmp/robustness-variable/configd_update.sh";
				configd:delete "/opt/vyatta/share/tmplscripts/interfaces/dataplane/ip/igmp/robustness-variable/configd_delete.sh";
			}
			leaf limit-exception {
				type uint32 {
					configd:syntax "/opt/vyatta/share/tmplscripts/interfaces/dataplane/ip/igmp/limit-exception/configd_syntax1.cli";
				}
				configd:help "Specify access-list that defines multicast groups that are exempted from being subject to configured limit";
				configd:allowed "/opt/vyatta/share/tmplscripts/interfaces/dataplane/ip/igmp/limit-exception/configd_allowed.sh";
				configd:update "/opt/vyatta/share/tmplscripts/interfaces/dataplane/ip/igmp/limit-exception/configd_update.sh";
				configd:delete "/opt/vyatta/share/tmplscripts/interfaces/dataplane/ip/igmp/limit-exception/configd_delete.sh";
				configd:validate "/opt/vyatta/share/tmplscripts/interfaces/dataplane/ip/igmp/limit-exception/configd_validate1.cli";
				configd:validate "/opt/vyatta/share/tmplscripts/interfaces/dataplane/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/dataplane/ip/igmp/limit/configd_update.sh";
				configd:delete "/opt/vyatta/share/tmplscripts/interfaces/dataplane/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/dataplane/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/dataplane/ip/igmp/last-member-query-count/configd_update.sh";
				configd:delete "/opt/vyatta/share/tmplscripts/interfaces/dataplane/ip/igmp/last-member-query-count/configd_delete.sh";
			}
			list static-group {
				configd:priority "780";
				configd:help "Set standard IP Multicast group address to be configured as a static group member";
				configd:create "/opt/vyatta/share/tmplscripts/interfaces/dataplane/ip/igmp/static-group/configd_create.sh";
				configd:end "/opt/vyatta/share/tmplscripts/interfaces/dataplane/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/dataplane/ip/igmp/static-group/source/configd_syntax1.cli";
					}
					ordered-by "user";
					configd:help "Configure standard IP source address as a static source from where multicast packets originate";
					configd:allowed "/opt/vyatta/share/tmplscripts/interfaces/dataplane/ip/igmp/static-group/source/configd_allowed.sh";
					configd:create "/opt/vyatta/share/tmplscripts/interfaces/dataplane/ip/igmp/static-group/source/configd_create.sh";
					configd:delete "/opt/vyatta/share/tmplscripts/interfaces/dataplane/ip/igmp/static-group/source/configd_delete.sh";
				}
			}
			list join-group {
				configd:help "Configure a join multicast group";
				configd:delete "/opt/vyatta/share/tmplscripts/interfaces/dataplane/ip/igmp/join-group/configd_delete.sh";
				configd:end "/opt/vyatta/share/tmplscripts/interfaces/dataplane/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/dataplane/ip/igmp/last-member-query-interval/configd_update.sh";
				configd:delete "/opt/vyatta/share/tmplscripts/interfaces/dataplane/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/dataplane/ip/igmp/version/configd_update.sh";
				configd:delete "/opt/vyatta/share/tmplscripts/interfaces/dataplane/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/dataplane/ip/igmp/access-group/configd_allowed.sh";
				configd:update "/opt/vyatta/share/tmplscripts/interfaces/dataplane/ip/igmp/access-group/configd_update.sh";
				configd:delete "/opt/vyatta/share/tmplscripts/interfaces/dataplane/ip/igmp/access-group/configd_delete.sh";
				configd:validate "/opt/vyatta/share/tmplscripts/interfaces/dataplane/ip/igmp/access-group/configd_validate1.cli";
			}
			leaf enforce-router-alert {
				type empty;
				configd:help "Enable strict RA (Router Advertisement) validation for IGMP";
				configd:create "/opt/vyatta/share/tmplscripts/interfaces/dataplane/ip/igmp/enforce-router-alert/configd_create.sh";
				configd:delete "/opt/vyatta/share/tmplscripts/interfaces/dataplane/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/dataplane/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/dataplane/ip/igmp/startup-query-count/configd_update.sh";
				configd:delete "/opt/vyatta/share/tmplscripts/interfaces/dataplane/ip/igmp/startup-query-count/configd_delete.sh";
			}
		}
	}
	augment /if:interfaces/interfaces-dataplane:dataplane/interfaces-dataplane:vif/interfaces-dataplane:ip {
		container igmp {
			presence "true";
			configd:help "Internet Group Management Protocol (IGMP)";
			configd:priority "462";
			configd:end "/opt/vyatta/share/tmplscripts/interfaces/dataplane/vif/ip/igmp/configd_end.sh";
			configd:validate "/opt/vyatta/share/tmplscripts/interfaces/dataplane/vif/ip/igmp/configd_validate1.cli";
			configd:validate "/opt/vyatta/share/tmplscripts/interfaces/dataplane/vif/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/dataplane/vif/ip/igmp/querier/querier-timeout/configd_update.sh";
					configd:delete "/opt/vyatta/share/tmplscripts/interfaces/dataplane/vif/ip/igmp/querier/querier-timeout/configd_delete.sh";
				}
			}
			leaf offlink {
				type empty;
				configd:help "Enable off-link for IGMP";
				configd:create "/opt/vyatta/share/tmplscripts/interfaces/dataplane/vif/ip/igmp/offlink/configd_create.sh";
				configd:delete "/opt/vyatta/share/tmplscripts/interfaces/dataplane/vif/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/dataplane/vif/ip/igmp/startup-query-interval/configd_update.sh";
				configd:delete "/opt/vyatta/share/tmplscripts/interfaces/dataplane/vif/ip/igmp/startup-query-interval/configd_delete.sh";
			}
			container immediate-leave {
				presence "true";
				configd:help "Immediate leave feature";
				configd:validate "/opt/vyatta/share/tmplscripts/interfaces/dataplane/vif/ip/igmp/immediate-leave/configd_validate1.cli";
				leaf group-list {
					type uint32 {
						configd:syntax "/opt/vyatta/share/tmplscripts/interfaces/dataplane/vif/ip/igmp/immediate-leave/group-list/configd_syntax1.cli";
					}
					configd:help "Defines multicast groups in which the immediate leave feature is enabled";
					configd:allowed "/opt/vyatta/share/tmplscripts/interfaces/dataplane/vif/ip/igmp/immediate-leave/group-list/configd_allowed.sh";
					configd:update "/opt/vyatta/share/tmplscripts/interfaces/dataplane/vif/ip/igmp/immediate-leave/group-list/configd_update.sh";
					configd:delete "/opt/vyatta/share/tmplscripts/interfaces/dataplane/vif/ip/igmp/immediate-leave/group-list/configd_delete.sh";
					configd:validate "/opt/vyatta/share/tmplscripts/interfaces/dataplane/vif/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/dataplane/vif/ip/igmp/robustness-variable/configd_update.sh";
				configd:delete "/opt/vyatta/share/tmplscripts/interfaces/dataplane/vif/ip/igmp/robustness-variable/configd_delete.sh";
			}
			leaf limit-exception {
				type uint32 {
					configd:syntax "/opt/vyatta/share/tmplscripts/interfaces/dataplane/vif/ip/igmp/limit-exception/configd_syntax1.cli";
				}
				configd:help "Specify access-list that defines multicast groups that are exempted from being subject to configured limit";
				configd:allowed "/opt/vyatta/share/tmplscripts/interfaces/dataplane/vif/ip/igmp/limit-exception/configd_allowed.sh";
				configd:update "/opt/vyatta/share/tmplscripts/interfaces/dataplane/vif/ip/igmp/limit-exception/configd_update.sh";
				configd:delete "/opt/vyatta/share/tmplscripts/interfaces/dataplane/vif/ip/igmp/limit-exception/configd_delete.sh";
				configd:validate "/opt/vyatta/share/tmplscripts/interfaces/dataplane/vif/ip/igmp/limit-exception/configd_validate1.cli";
				configd:validate "/opt/vyatta/share/tmplscripts/interfaces/dataplane/vif/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/dataplane/vif/ip/igmp/limit/configd_update.sh";
				configd:delete "/opt/vyatta/share/tmplscripts/interfaces/dataplane/vif/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/dataplane/vif/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/dataplane/vif/ip/igmp/last-member-query-count/configd_update.sh";
				configd:delete "/opt/vyatta/share/tmplscripts/interfaces/dataplane/vif/ip/igmp/last-member-query-count/configd_delete.sh";
			}
			list static-group {
				configd:priority "780";
				configd:help "Set standard IP Multicast group address to be configured as a static group member";
				configd:create "/opt/vyatta/share/tmplscripts/interfaces/dataplane/vif/ip/igmp/static-group/configd_create.sh";
				configd:end "/opt/vyatta/share/tmplscripts/interfaces/dataplane/vif/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/dataplane/vif/ip/igmp/static-group/source/configd_syntax1.cli";
					}
					ordered-by "user";
					configd:help "Configure standard IP source address as a static source from where multicast packets originate";
					configd:allowed "/opt/vyatta/share/tmplscripts/interfaces/dataplane/vif/ip/igmp/static-group/source/configd_allowed.sh";
					configd:create "/opt/vyatta/share/tmplscripts/interfaces/dataplane/vif/ip/igmp/static-group/source/configd_create.sh";
					configd:delete "/opt/vyatta/share/tmplscripts/interfaces/dataplane/vif/ip/igmp/static-group/source/configd_delete.sh";
				}
			}
			list join-group {
				configd:help "Configure a join multicast group";
				configd:delete "/opt/vyatta/share/tmplscripts/interfaces/dataplane/vif/ip/igmp/join-group/configd_delete.sh";
				configd:end "/opt/vyatta/share/tmplscripts/interfaces/dataplane/vif/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/dataplane/vif/ip/igmp/last-member-query-interval/configd_update.sh";
				configd:delete "/opt/vyatta/share/tmplscripts/interfaces/dataplane/vif/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/dataplane/vif/ip/igmp/version/configd_update.sh";
				configd:delete "/opt/vyatta/share/tmplscripts/interfaces/dataplane/vif/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/dataplane/vif/ip/igmp/access-group/configd_allowed.sh";
				configd:update "/opt/vyatta/share/tmplscripts/interfaces/dataplane/vif/ip/igmp/access-group/configd_update.sh";
				configd:delete "/opt/vyatta/share/tmplscripts/interfaces/dataplane/vif/ip/igmp/access-group/configd_delete.sh";
				configd:validate "/opt/vyatta/share/tmplscripts/interfaces/dataplane/vif/ip/igmp/access-group/configd_validate1.cli";
			}
			leaf enforce-router-alert {
				type empty;
				configd:help "Enable strict RA (Router Advertisement) validation for IGMP";
				configd:create "/opt/vyatta/share/tmplscripts/interfaces/dataplane/vif/ip/igmp/enforce-router-alert/configd_create.sh";
				configd:delete "/opt/vyatta/share/tmplscripts/interfaces/dataplane/vif/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/dataplane/vif/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/dataplane/vif/ip/igmp/startup-query-count/configd_update.sh";
				configd:delete "/opt/vyatta/share/tmplscripts/interfaces/dataplane/vif/ip/igmp/startup-query-count/configd_delete.sh";
			}
		}
	}
	augment /if:interfaces/interfaces-l2tpeth:l2tpeth/interfaces-l2tpeth:ip {
		container igmp {
			presence "true";
			configd:help "Internet Group Management Protocol (IGMP)";
			configd:priority "462";
			configd:end "/opt/vyatta/share/tmplscripts/interfaces/l2tpeth/ip/igmp/configd_end.sh";
			configd:validate "/opt/vyatta/share/tmplscripts/interfaces/l2tpeth/ip/igmp/configd_validate1.cli";
			configd:validate "/opt/vyatta/share/tmplscripts/interfaces/l2tpeth/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/l2tpeth/ip/igmp/querier/querier-timeout/configd_update.sh";
					configd:delete "/opt/vyatta/share/tmplscripts/interfaces/l2tpeth/ip/igmp/querier/querier-timeout/configd_delete.sh";
				}
			}
			leaf offlink {
				type empty;
				configd:help "Enable off-link for IGMP";
				configd:create "/opt/vyatta/share/tmplscripts/interfaces/l2tpeth/ip/igmp/offlink/configd_create.sh";
				configd:delete "/opt/vyatta/share/tmplscripts/interfaces/l2tpeth/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/l2tpeth/ip/igmp/startup-query-interval/configd_update.sh";
				configd:delete "/opt/vyatta/share/tmplscripts/interfaces/l2tpeth/ip/igmp/startup-query-interval/configd_delete.sh";
			}
			container immediate-leave {
				presence "true";
				configd:help "Immediate leave feature";
				configd:validate "/opt/vyatta/share/tmplscripts/interfaces/l2tpeth/ip/igmp/immediate-leave/configd_validate1.cli";
				leaf group-list {
					type uint32 {
						configd:syntax "/opt/vyatta/share/tmplscripts/interfaces/l2tpeth/ip/igmp/immediate-leave/group-list/configd_syntax1.cli";
					}
					configd:help "Defines multicast groups in which the immediate leave feature is enabled";
					configd:allowed "/opt/vyatta/share/tmplscripts/interfaces/l2tpeth/ip/igmp/immediate-leave/group-list/configd_allowed.sh";
					configd:update "/opt/vyatta/share/tmplscripts/interfaces/l2tpeth/ip/igmp/immediate-leave/group-list/configd_update.sh";
					configd:delete "/opt/vyatta/share/tmplscripts/interfaces/l2tpeth/ip/igmp/immediate-leave/group-list/configd_delete.sh";
					configd:validate "/opt/vyatta/share/tmplscripts/interfaces/l2tpeth/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/l2tpeth/ip/igmp/robustness-variable/configd_update.sh";
				configd:delete "/opt/vyatta/share/tmplscripts/interfaces/l2tpeth/ip/igmp/robustness-variable/configd_delete.sh";
			}
			leaf limit-exception {
				type uint32 {
					configd:syntax "/opt/vyatta/share/tmplscripts/interfaces/l2tpeth/ip/igmp/limit-exception/configd_syntax1.cli";
				}
				configd:help "Specify access-list that defines multicast groups that are exempted from being subject to configured limit";
				configd:allowed "/opt/vyatta/share/tmplscripts/interfaces/l2tpeth/ip/igmp/limit-exception/configd_allowed.sh";
				configd:update "/opt/vyatta/share/tmplscripts/interfaces/l2tpeth/ip/igmp/limit-exception/configd_update.sh";
				configd:delete "/opt/vyatta/share/tmplscripts/interfaces/l2tpeth/ip/igmp/limit-exception/configd_delete.sh";
				configd:validate "/opt/vyatta/share/tmplscripts/interfaces/l2tpeth/ip/igmp/limit-exception/configd_validate1.cli";
				configd:validate "/opt/vyatta/share/tmplscripts/interfaces/l2tpeth/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/l2tpeth/ip/igmp/limit/configd_update.sh";
				configd:delete "/opt/vyatta/share/tmplscripts/interfaces/l2tpeth/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/l2tpeth/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/l2tpeth/ip/igmp/last-member-query-count/configd_update.sh";
				configd:delete "/opt/vyatta/share/tmplscripts/interfaces/l2tpeth/ip/igmp/last-member-query-count/configd_delete.sh";
			}
			list static-group {
				configd:priority "780";
				configd:help "Set standard IP Multicast group address to be configured as a static group member";
				configd:create "/opt/vyatta/share/tmplscripts/interfaces/l2tpeth/ip/igmp/static-group/configd_create.sh";
				configd:end "/opt/vyatta/share/tmplscripts/interfaces/l2tpeth/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/l2tpeth/ip/igmp/static-group/source/configd_syntax1.cli";
					}
					ordered-by "user";
					configd:help "Configure standard IP source address as a static source from where multicast packets originate";
					configd:allowed "/opt/vyatta/share/tmplscripts/interfaces/l2tpeth/ip/igmp/static-group/source/configd_allowed.sh";
					configd:create "/opt/vyatta/share/tmplscripts/interfaces/l2tpeth/ip/igmp/static-group/source/configd_create.sh";
					configd:delete "/opt/vyatta/share/tmplscripts/interfaces/l2tpeth/ip/igmp/static-group/source/configd_delete.sh";
				}
			}
			list join-group {
				configd:help "Configure a join multicast group";
				configd:delete "/opt/vyatta/share/tmplscripts/interfaces/l2tpeth/ip/igmp/join-group/configd_delete.sh";
				configd:end "/opt/vyatta/share/tmplscripts/interfaces/l2tpeth/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/l2tpeth/ip/igmp/last-member-query-interval/configd_update.sh";
				configd:delete "/opt/vyatta/share/tmplscripts/interfaces/l2tpeth/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/l2tpeth/ip/igmp/version/configd_update.sh";
				configd:delete "/opt/vyatta/share/tmplscripts/interfaces/l2tpeth/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/l2tpeth/ip/igmp/access-group/configd_allowed.sh";
				configd:update "/opt/vyatta/share/tmplscripts/interfaces/l2tpeth/ip/igmp/access-group/configd_update.sh";
				configd:delete "/opt/vyatta/share/tmplscripts/interfaces/l2tpeth/ip/igmp/access-group/configd_delete.sh";
				configd:validate "/opt/vyatta/share/tmplscripts/interfaces/l2tpeth/ip/igmp/access-group/configd_validate1.cli";
			}
			leaf enforce-router-alert {
				type empty;
				configd:help "Enable strict RA (Router Advertisement) validation for IGMP";
				configd:create "/opt/vyatta/share/tmplscripts/interfaces/l2tpeth/ip/igmp/enforce-router-alert/configd_create.sh";
				configd:delete "/opt/vyatta/share/tmplscripts/interfaces/l2tpeth/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/l2tpeth/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/l2tpeth/ip/igmp/startup-query-count/configd_update.sh";
				configd:delete "/opt/vyatta/share/tmplscripts/interfaces/l2tpeth/ip/igmp/startup-query-count/configd_delete.sh";
			}
		}
	}
	augment /if:interfaces/interfaces-l2tpeth:l2tpeth/interfaces-l2tpeth:vif/interfaces-l2tpeth:ip {
		container igmp {
			presence "true";
			configd:help "Internet Group Management Protocol (IGMP)";
			configd:priority "462";
			configd:end "/opt/vyatta/share/tmplscripts/interfaces/l2tpeth/vif/ip/igmp/configd_end.sh";
			configd:validate "/opt/vyatta/share/tmplscripts/interfaces/l2tpeth/vif/ip/igmp/configd_validate1.cli";
			configd:validate "/opt/vyatta/share/tmplscripts/interfaces/l2tpeth/vif/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/l2tpeth/vif/ip/igmp/querier/querier-timeout/configd_update.sh";
					configd:delete "/opt/vyatta/share/tmplscripts/interfaces/l2tpeth/vif/ip/igmp/querier/querier-timeout/configd_delete.sh";
				}
			}
			leaf offlink {
				type empty;
				configd:help "Enable off-link for IGMP";
				configd:create "/opt/vyatta/share/tmplscripts/interfaces/l2tpeth/vif/ip/igmp/offlink/configd_create.sh";
				configd:delete "/opt/vyatta/share/tmplscripts/interfaces/l2tpeth/vif/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/l2tpeth/vif/ip/igmp/startup-query-interval/configd_update.sh";
				configd:delete "/opt/vyatta/share/tmplscripts/interfaces/l2tpeth/vif/ip/igmp/startup-query-interval/configd_delete.sh";
			}
			container immediate-leave {
				presence "true";
				configd:help "Immediate leave feature";
				configd:validate "/opt/vyatta/share/tmplscripts/interfaces/l2tpeth/vif/ip/igmp/immediate-leave/configd_validate1.cli";
				leaf group-list {
					type uint32 {
						configd:syntax "/opt/vyatta/share/tmplscripts/interfaces/l2tpeth/vif/ip/igmp/immediate-leave/group-list/configd_syntax1.cli";
					}
					configd:help "Defines multicast groups in which the immediate leave feature is enabled";
					configd:allowed "/opt/vyatta/share/tmplscripts/interfaces/l2tpeth/vif/ip/igmp/immediate-leave/group-list/configd_allowed.sh";
					configd:update "/opt/vyatta/share/tmplscripts/interfaces/l2tpeth/vif/ip/igmp/immediate-leave/group-list/configd_update.sh";
					configd:delete "/opt/vyatta/share/tmplscripts/interfaces/l2tpeth/vif/ip/igmp/immediate-leave/group-list/configd_delete.sh";
					configd:validate "/opt/vyatta/share/tmplscripts/interfaces/l2tpeth/vif/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/l2tpeth/vif/ip/igmp/robustness-variable/configd_update.sh";
				configd:delete "/opt/vyatta/share/tmplscripts/interfaces/l2tpeth/vif/ip/igmp/robustness-variable/configd_delete.sh";
			}
			leaf limit-exception {
				type uint32 {
					configd:syntax "/opt/vyatta/share/tmplscripts/interfaces/l2tpeth/vif/ip/igmp/limit-exception/configd_syntax1.cli";
				}
				configd:help "Specify access-list that defines multicast groups that are exempted from being subject to configured limit";
				configd:allowed "/opt/vyatta/share/tmplscripts/interfaces/l2tpeth/vif/ip/igmp/limit-exception/configd_allowed.sh";
				configd:update "/opt/vyatta/share/tmplscripts/interfaces/l2tpeth/vif/ip/igmp/limit-exception/configd_update.sh";
				configd:delete "/opt/vyatta/share/tmplscripts/interfaces/l2tpeth/vif/ip/igmp/limit-exception/configd_delete.sh";
				configd:validate "/opt/vyatta/share/tmplscripts/interfaces/l2tpeth/vif/ip/igmp/limit-exception/configd_validate1.cli";
				configd:validate "/opt/vyatta/share/tmplscripts/interfaces/l2tpeth/vif/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/l2tpeth/vif/ip/igmp/limit/configd_update.sh";
				configd:delete "/opt/vyatta/share/tmplscripts/interfaces/l2tpeth/vif/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/l2tpeth/vif/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/l2tpeth/vif/ip/igmp/last-member-query-count/configd_update.sh";
				configd:delete "/opt/vyatta/share/tmplscripts/interfaces/l2tpeth/vif/ip/igmp/last-member-query-count/configd_delete.sh";
			}
			list static-group {
				configd:priority "780";
				configd:help "Set standard IP Multicast group address to be configured as a static group member";
				configd:create "/opt/vyatta/share/tmplscripts/interfaces/l2tpeth/vif/ip/igmp/static-group/configd_create.sh";
				configd:end "/opt/vyatta/share/tmplscripts/interfaces/l2tpeth/vif/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/l2tpeth/vif/ip/igmp/static-group/source/configd_syntax1.cli";
					}
					ordered-by "user";
					configd:help "Configure standard IP source address as a static source from where multicast packets originate";
					configd:allowed "/opt/vyatta/share/tmplscripts/interfaces/l2tpeth/vif/ip/igmp/static-group/source/configd_allowed.sh";
					configd:create "/opt/vyatta/share/tmplscripts/interfaces/l2tpeth/vif/ip/igmp/static-group/source/configd_create.sh";
					configd:delete "/opt/vyatta/share/tmplscripts/interfaces/l2tpeth/vif/ip/igmp/static-group/source/configd_delete.sh";
				}
			}
			list join-group {
				configd:help "Configure a join multicast group";
				configd:delete "/opt/vyatta/share/tmplscripts/interfaces/l2tpeth/vif/ip/igmp/join-group/configd_delete.sh";
				configd:end "/opt/vyatta/share/tmplscripts/interfaces/l2tpeth/vif/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/l2tpeth/vif/ip/igmp/last-member-query-interval/configd_update.sh";
				configd:delete "/opt/vyatta/share/tmplscripts/interfaces/l2tpeth/vif/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/l2tpeth/vif/ip/igmp/version/configd_update.sh";
				configd:delete "/opt/vyatta/share/tmplscripts/interfaces/l2tpeth/vif/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/l2tpeth/vif/ip/igmp/access-group/configd_allowed.sh";
				configd:update "/opt/vyatta/share/tmplscripts/interfaces/l2tpeth/vif/ip/igmp/access-group/configd_update.sh";
				configd:delete "/opt/vyatta/share/tmplscripts/interfaces/l2tpeth/vif/ip/igmp/access-group/configd_delete.sh";
				configd:validate "/opt/vyatta/share/tmplscripts/interfaces/l2tpeth/vif/ip/igmp/access-group/configd_validate1.cli";
			}
			leaf enforce-router-alert {
				type empty;
				configd:help "Enable strict RA (Router Advertisement) validation for IGMP";
				configd:create "/opt/vyatta/share/tmplscripts/interfaces/l2tpeth/vif/ip/igmp/enforce-router-alert/configd_create.sh";
				configd:delete "/opt/vyatta/share/tmplscripts/interfaces/l2tpeth/vif/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/l2tpeth/vif/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/l2tpeth/vif/ip/igmp/startup-query-count/configd_update.sh";
				configd:delete "/opt/vyatta/share/tmplscripts/interfaces/l2tpeth/vif/ip/igmp/startup-query-count/configd_delete.sh";
			}
		}
	}
	augment /if:interfaces/interfaces-loopback:loopback/interfaces-loopback:ip {
		container igmp {
			presence "true";
			configd:help "Internet Group Management Protocol (IGMP)";
			configd:priority "462";
			configd:end "/opt/vyatta/share/tmplscripts/interfaces/loopback/ip/igmp/configd_end.sh";
			configd:validate "/opt/vyatta/share/tmplscripts/interfaces/loopback/ip/igmp/configd_validate1.cli";
			configd:validate "/opt/vyatta/share/tmplscripts/interfaces/loopback/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/loopback/ip/igmp/querier/querier-timeout/configd_update.sh";
					configd:delete "/opt/vyatta/share/tmplscripts/interfaces/loopback/ip/igmp/querier/querier-timeout/configd_delete.sh";
				}
			}
			leaf offlink {
				type empty;
				configd:help "Enable off-link for IGMP";
				configd:create "/opt/vyatta/share/tmplscripts/interfaces/loopback/ip/igmp/offlink/configd_create.sh";
				configd:delete "/opt/vyatta/share/tmplscripts/interfaces/loopback/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/loopback/ip/igmp/startup-query-interval/configd_update.sh";
				configd:delete "/opt/vyatta/share/tmplscripts/interfaces/loopback/ip/igmp/startup-query-interval/configd_delete.sh";
			}
			container immediate-leave {
				presence "true";
				configd:help "Immediate leave feature";
				configd:validate "/opt/vyatta/share/tmplscripts/interfaces/loopback/ip/igmp/immediate-leave/configd_validate1.cli";
				leaf group-list {
					type uint32 {
						configd:syntax "/opt/vyatta/share/tmplscripts/interfaces/loopback/ip/igmp/immediate-leave/group-list/configd_syntax1.cli";
					}
					configd:help "Defines multicast groups in which the immediate leave feature is enabled";
					configd:allowed "/opt/vyatta/share/tmplscripts/interfaces/loopback/ip/igmp/immediate-leave/group-list/configd_allowed.sh";
					configd:update "/opt/vyatta/share/tmplscripts/interfaces/loopback/ip/igmp/immediate-leave/group-list/configd_update.sh";
					configd:delete "/opt/vyatta/share/tmplscripts/interfaces/loopback/ip/igmp/immediate-leave/group-list/configd_delete.sh";
					configd:validate "/opt/vyatta/share/tmplscripts/interfaces/loopback/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/loopback/ip/igmp/robustness-variable/configd_update.sh";
				configd:delete "/opt/vyatta/share/tmplscripts/interfaces/loopback/ip/igmp/robustness-variable/configd_delete.sh";
			}
			leaf limit-exception {
				type uint32 {
					configd:syntax "/opt/vyatta/share/tmplscripts/interfaces/loopback/ip/igmp/limit-exception/configd_syntax1.cli";
				}
				configd:help "Specify access-list that defines multicast groups that are exempted from being subject to configured limit";
				configd:allowed "/opt/vyatta/share/tmplscripts/interfaces/loopback/ip/igmp/limit-exception/configd_allowed.sh";
				configd:update "/opt/vyatta/share/tmplscripts/interfaces/loopback/ip/igmp/limit-exception/configd_update.sh";
				configd:delete "/opt/vyatta/share/tmplscripts/interfaces/loopback/ip/igmp/limit-exception/configd_delete.sh";
				configd:validate "/opt/vyatta/share/tmplscripts/interfaces/loopback/ip/igmp/limit-exception/configd_validate1.cli";
				configd:validate "/opt/vyatta/share/tmplscripts/interfaces/loopback/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/loopback/ip/igmp/limit/configd_update.sh";
				configd:delete "/opt/vyatta/share/tmplscripts/interfaces/loopback/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/loopback/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/loopback/ip/igmp/last-member-query-count/configd_update.sh";
				configd:delete "/opt/vyatta/share/tmplscripts/interfaces/loopback/ip/igmp/last-member-query-count/configd_delete.sh";
			}
			list static-group {
				configd:priority "780";
				configd:help "Set standard IP Multicast group address to be configured as a static group member";
				configd:create "/opt/vyatta/share/tmplscripts/interfaces/loopback/ip/igmp/static-group/configd_create.sh";
				configd:end "/opt/vyatta/share/tmplscripts/interfaces/loopback/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/loopback/ip/igmp/static-group/source/configd_syntax1.cli";
					}
					ordered-by "user";
					configd:help "Configure standard IP source address as a static source from where multicast packets originate";
					configd:allowed "/opt/vyatta/share/tmplscripts/interfaces/loopback/ip/igmp/static-group/source/configd_allowed.sh";
					configd:create "/opt/vyatta/share/tmplscripts/interfaces/loopback/ip/igmp/static-group/source/configd_create.sh";
					configd:delete "/opt/vyatta/share/tmplscripts/interfaces/loopback/ip/igmp/static-group/source/configd_delete.sh";
				}
			}
			list join-group {
				configd:help "Configure a join multicast group";
				configd:delete "/opt/vyatta/share/tmplscripts/interfaces/loopback/ip/igmp/join-group/configd_delete.sh";
				configd:end "/opt/vyatta/share/tmplscripts/interfaces/loopback/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/loopback/ip/igmp/last-member-query-interval/configd_update.sh";
				configd:delete "/opt/vyatta/share/tmplscripts/interfaces/loopback/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/loopback/ip/igmp/version/configd_update.sh";
				configd:delete "/opt/vyatta/share/tmplscripts/interfaces/loopback/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/loopback/ip/igmp/access-group/configd_allowed.sh";
				configd:update "/opt/vyatta/share/tmplscripts/interfaces/loopback/ip/igmp/access-group/configd_update.sh";
				configd:delete "/opt/vyatta/share/tmplscripts/interfaces/loopback/ip/igmp/access-group/configd_delete.sh";
				configd:validate "/opt/vyatta/share/tmplscripts/interfaces/loopback/ip/igmp/access-group/configd_validate1.cli";
			}
			leaf enforce-router-alert {
				type empty;
				configd:help "Enable strict RA (Router Advertisement) validation for IGMP";
				configd:create "/opt/vyatta/share/tmplscripts/interfaces/loopback/ip/igmp/enforce-router-alert/configd_create.sh";
				configd:delete "/opt/vyatta/share/tmplscripts/interfaces/loopback/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/loopback/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/loopback/ip/igmp/startup-query-count/configd_update.sh";
				configd:delete "/opt/vyatta/share/tmplscripts/interfaces/loopback/ip/igmp/startup-query-count/configd_delete.sh";
			}
		}
	}
	augment /if:interfaces/interfaces-openvpn:openvpn/interfaces-openvpn:ip {
		container igmp {
			presence "true";
			configd:help "Internet Group Management Protocol (IGMP)";
			configd:priority "462";
			configd:end "/opt/vyatta/share/tmplscripts/interfaces/openvpn/ip/igmp/configd_end.sh";
			configd:validate "/opt/vyatta/share/tmplscripts/interfaces/openvpn/ip/igmp/configd_validate1.cli";
			configd:validate "/opt/vyatta/share/tmplscripts/interfaces/openvpn/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/openvpn/ip/igmp/querier/querier-timeout/configd_update.sh";
					configd:delete "/opt/vyatta/share/tmplscripts/interfaces/openvpn/ip/igmp/querier/querier-timeout/configd_delete.sh";
				}
			}
			leaf offlink {
				type empty;
				configd:help "Enable off-link for IGMP";
				configd:create "/opt/vyatta/share/tmplscripts/interfaces/openvpn/ip/igmp/offlink/configd_create.sh";
				configd:delete "/opt/vyatta/share/tmplscripts/interfaces/openvpn/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/openvpn/ip/igmp/startup-query-interval/configd_update.sh";
				configd:delete "/opt/vyatta/share/tmplscripts/interfaces/openvpn/ip/igmp/startup-query-interval/configd_delete.sh";
			}
			container immediate-leave {
				presence "true";
				configd:help "Immediate leave feature";
				configd:validate "/opt/vyatta/share/tmplscripts/interfaces/openvpn/ip/igmp/immediate-leave/configd_validate1.cli";
				leaf group-list {
					type uint32 {
						configd:syntax "/opt/vyatta/share/tmplscripts/interfaces/openvpn/ip/igmp/immediate-leave/group-list/configd_syntax1.cli";
					}
					configd:help "Defines multicast groups in which the immediate leave feature is enabled";
					configd:allowed "/opt/vyatta/share/tmplscripts/interfaces/openvpn/ip/igmp/immediate-leave/group-list/configd_allowed.sh";
					configd:update "/opt/vyatta/share/tmplscripts/interfaces/openvpn/ip/igmp/immediate-leave/group-list/configd_update.sh";
					configd:delete "/opt/vyatta/share/tmplscripts/interfaces/openvpn/ip/igmp/immediate-leave/group-list/configd_delete.sh";
					configd:validate "/opt/vyatta/share/tmplscripts/interfaces/openvpn/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/openvpn/ip/igmp/robustness-variable/configd_update.sh";
				configd:delete "/opt/vyatta/share/tmplscripts/interfaces/openvpn/ip/igmp/robustness-variable/configd_delete.sh";
			}
			leaf limit-exception {
				type uint32 {
					configd:syntax "/opt/vyatta/share/tmplscripts/interfaces/openvpn/ip/igmp/limit-exception/configd_syntax1.cli";
				}
				configd:help "Specify access-list that defines multicast groups that are exempted from being subject to configured limit";
				configd:allowed "/opt/vyatta/share/tmplscripts/interfaces/openvpn/ip/igmp/limit-exception/configd_allowed.sh";
				configd:update "/opt/vyatta/share/tmplscripts/interfaces/openvpn/ip/igmp/limit-exception/configd_update.sh";
				configd:delete "/opt/vyatta/share/tmplscripts/interfaces/openvpn/ip/igmp/limit-exception/configd_delete.sh";
				configd:validate "/opt/vyatta/share/tmplscripts/interfaces/openvpn/ip/igmp/limit-exception/configd_validate1.cli";
				configd:validate "/opt/vyatta/share/tmplscripts/interfaces/openvpn/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/openvpn/ip/igmp/limit/configd_update.sh";
				configd:delete "/opt/vyatta/share/tmplscripts/interfaces/openvpn/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/openvpn/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/openvpn/ip/igmp/last-member-query-count/configd_update.sh";
				configd:delete "/opt/vyatta/share/tmplscripts/interfaces/openvpn/ip/igmp/last-member-query-count/configd_delete.sh";
			}
			list static-group {
				configd:priority "780";
				configd:help "Set standard IP Multicast group address to be configured as a static group member";
				configd:create "/opt/vyatta/share/tmplscripts/interfaces/openvpn/ip/igmp/static-group/configd_create.sh";
				configd:end "/opt/vyatta/share/tmplscripts/interfaces/openvpn/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/openvpn/ip/igmp/static-group/source/configd_syntax1.cli";
					}
					ordered-by "user";
					configd:help "Configure standard IP source address as a static source from where multicast packets originate";
					configd:allowed "/opt/vyatta/share/tmplscripts/interfaces/openvpn/ip/igmp/static-group/source/configd_allowed.sh";
					configd:create "/opt/vyatta/share/tmplscripts/interfaces/openvpn/ip/igmp/static-group/source/configd_create.sh";
					configd:delete "/opt/vyatta/share/tmplscripts/interfaces/openvpn/ip/igmp/static-group/source/configd_delete.sh";
				}
			}
			list join-group {
				configd:help "Configure a join multicast group";
				configd:delete "/opt/vyatta/share/tmplscripts/interfaces/openvpn/ip/igmp/join-group/configd_delete.sh";
				configd:end "/opt/vyatta/share/tmplscripts/interfaces/openvpn/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/openvpn/ip/igmp/last-member-query-interval/configd_update.sh";
				configd:delete "/opt/vyatta/share/tmplscripts/interfaces/openvpn/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/openvpn/ip/igmp/version/configd_update.sh";
				configd:delete "/opt/vyatta/share/tmplscripts/interfaces/openvpn/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/openvpn/ip/igmp/access-group/configd_allowed.sh";
				configd:update "/opt/vyatta/share/tmplscripts/interfaces/openvpn/ip/igmp/access-group/configd_update.sh";
				configd:delete "/opt/vyatta/share/tmplscripts/interfaces/openvpn/ip/igmp/access-group/configd_delete.sh";
				configd:validate "/opt/vyatta/share/tmplscripts/interfaces/openvpn/ip/igmp/access-group/configd_validate1.cli";
			}
			leaf enforce-router-alert {
				type empty;
				configd:help "Enable strict RA (Router Advertisement) validation for IGMP";
				configd:create "/opt/vyatta/share/tmplscripts/interfaces/openvpn/ip/igmp/enforce-router-alert/configd_create.sh";
				configd:delete "/opt/vyatta/share/tmplscripts/interfaces/openvpn/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/openvpn/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/openvpn/ip/igmp/startup-query-count/configd_update.sh";
				configd:delete "/opt/vyatta/share/tmplscripts/interfaces/openvpn/ip/igmp/startup-query-count/configd_delete.sh";
			}
		}
	}
	augment /if:interfaces/interfaces-tunnel:tunnel/interfaces-tunnel:ip {
		container igmp {
			presence "true";
			configd:help "Internet Group Management Protocol (IGMP)";
			configd:priority "462";
			configd:end "/opt/vyatta/share/tmplscripts/interfaces/tunnel/ip/igmp/configd_end.sh";
			configd:validate "/opt/vyatta/share/tmplscripts/interfaces/tunnel/ip/igmp/configd_validate1.cli";
			configd:validate "/opt/vyatta/share/tmplscripts/interfaces/tunnel/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/tunnel/ip/igmp/querier/querier-timeout/configd_update.sh";
					configd:delete "/opt/vyatta/share/tmplscripts/interfaces/tunnel/ip/igmp/querier/querier-timeout/configd_delete.sh";
				}
			}
			leaf offlink {
				type empty;
				configd:help "Enable off-link for IGMP";
				configd:create "/opt/vyatta/share/tmplscripts/interfaces/tunnel/ip/igmp/offlink/configd_create.sh";
				configd:delete "/opt/vyatta/share/tmplscripts/interfaces/tunnel/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/tunnel/ip/igmp/startup-query-interval/configd_update.sh";
				configd:delete "/opt/vyatta/share/tmplscripts/interfaces/tunnel/ip/igmp/startup-query-interval/configd_delete.sh";
			}
			container immediate-leave {
				presence "true";
				configd:help "Immediate leave feature";
				configd:validate "/opt/vyatta/share/tmplscripts/interfaces/tunnel/ip/igmp/immediate-leave/configd_validate1.cli";
				leaf group-list {
					type uint32 {
						configd:syntax "/opt/vyatta/share/tmplscripts/interfaces/tunnel/ip/igmp/immediate-leave/group-list/configd_syntax1.cli";
					}
					configd:help "Defines multicast groups in which the immediate leave feature is enabled";
					configd:allowed "/opt/vyatta/share/tmplscripts/interfaces/tunnel/ip/igmp/immediate-leave/group-list/configd_allowed.sh";
					configd:update "/opt/vyatta/share/tmplscripts/interfaces/tunnel/ip/igmp/immediate-leave/group-list/configd_update.sh";
					configd:delete "/opt/vyatta/share/tmplscripts/interfaces/tunnel/ip/igmp/immediate-leave/group-list/configd_delete.sh";
					configd:validate "/opt/vyatta/share/tmplscripts/interfaces/tunnel/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/tunnel/ip/igmp/robustness-variable/configd_update.sh";
				configd:delete "/opt/vyatta/share/tmplscripts/interfaces/tunnel/ip/igmp/robustness-variable/configd_delete.sh";
			}
			leaf limit-exception {
				type uint32 {
					configd:syntax "/opt/vyatta/share/tmplscripts/interfaces/tunnel/ip/igmp/limit-exception/configd_syntax1.cli";
				}
				configd:help "Specify access-list that defines multicast groups that are exempted from being subject to configured limit";
				configd:allowed "/opt/vyatta/share/tmplscripts/interfaces/tunnel/ip/igmp/limit-exception/configd_allowed.sh";
				configd:update "/opt/vyatta/share/tmplscripts/interfaces/tunnel/ip/igmp/limit-exception/configd_update.sh";
				configd:delete "/opt/vyatta/share/tmplscripts/interfaces/tunnel/ip/igmp/limit-exception/configd_delete.sh";
				configd:validate "/opt/vyatta/share/tmplscripts/interfaces/tunnel/ip/igmp/limit-exception/configd_validate1.cli";
				configd:validate "/opt/vyatta/share/tmplscripts/interfaces/tunnel/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/tunnel/ip/igmp/limit/configd_update.sh";
				configd:delete "/opt/vyatta/share/tmplscripts/interfaces/tunnel/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/tunnel/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/tunnel/ip/igmp/last-member-query-count/configd_update.sh";
				configd:delete "/opt/vyatta/share/tmplscripts/interfaces/tunnel/ip/igmp/last-member-query-count/configd_delete.sh";
			}
			list static-group {
				configd:priority "780";
				configd:help "Set standard IP Multicast group address to be configured as a static group member";
				configd:create "/opt/vyatta/share/tmplscripts/interfaces/tunnel/ip/igmp/static-group/configd_create.sh";
				configd:end "/opt/vyatta/share/tmplscripts/interfaces/tunnel/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/tunnel/ip/igmp/static-group/source/configd_syntax1.cli";
					}
					ordered-by "user";
					configd:help "Configure standard IP source address as a static source from where multicast packets originate";
					configd:allowed "/opt/vyatta/share/tmplscripts/interfaces/tunnel/ip/igmp/static-group/source/configd_allowed.sh";
					configd:create "/opt/vyatta/share/tmplscripts/interfaces/tunnel/ip/igmp/static-group/source/configd_create.sh";
					configd:delete "/opt/vyatta/share/tmplscripts/interfaces/tunnel/ip/igmp/static-group/source/configd_delete.sh";
				}
			}
			list join-group {
				configd:help "Configure a join multicast group";
				configd:delete "/opt/vyatta/share/tmplscripts/interfaces/tunnel/ip/igmp/join-group/configd_delete.sh";
				configd:end "/opt/vyatta/share/tmplscripts/interfaces/tunnel/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/tunnel/ip/igmp/last-member-query-interval/configd_update.sh";
				configd:delete "/opt/vyatta/share/tmplscripts/interfaces/tunnel/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/tunnel/ip/igmp/version/configd_update.sh";
				configd:delete "/opt/vyatta/share/tmplscripts/interfaces/tunnel/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/tunnel/ip/igmp/access-group/configd_allowed.sh";
				configd:update "/opt/vyatta/share/tmplscripts/interfaces/tunnel/ip/igmp/access-group/configd_update.sh";
				configd:delete "/opt/vyatta/share/tmplscripts/interfaces/tunnel/ip/igmp/access-group/configd_delete.sh";
				configd:validate "/opt/vyatta/share/tmplscripts/interfaces/tunnel/ip/igmp/access-group/configd_validate1.cli";
			}
			leaf enforce-router-alert {
				type empty;
				configd:help "Enable strict RA (Router Advertisement) validation for IGMP";
				configd:create "/opt/vyatta/share/tmplscripts/interfaces/tunnel/ip/igmp/enforce-router-alert/configd_create.sh";
				configd:delete "/opt/vyatta/share/tmplscripts/interfaces/tunnel/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/tunnel/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/tunnel/ip/igmp/startup-query-count/configd_update.sh";
				configd:delete "/opt/vyatta/share/tmplscripts/interfaces/tunnel/ip/igmp/startup-query-count/configd_delete.sh";
			}
		}
	}
	augment /if:interfaces/interfaces-vti:vti/interfaces-vti:ip {
		container igmp {
			presence "true";
			configd:help "Internet Group Management Protocol (IGMP)";
			configd:priority "462";
			configd:end "/opt/vyatta/share/tmplscripts/interfaces/vti/ip/igmp/configd_end.sh";
			configd:validate "/opt/vyatta/share/tmplscripts/interfaces/vti/ip/igmp/configd_validate1.cli";
			configd:validate "/opt/vyatta/share/tmplscripts/interfaces/vti/ip/igmp/configd_validate2.cli";
			container querier {
				presence "true";
				configd:help "Querier mode";
				leaf forced {
					type empty;
					configd:help "Set forced querier mode";
				}
				leaf querier-timeout {
					type uint32 {
						range 60..300 {
							error-message "Must be between 60-300";
						}
					}
					configd:help "Period that router waits before assuming querier role";
					configd:update "/opt/vyatta/share/tmplscripts/interfaces/vti/ip/igmp/querier/querier-timeout/configd_update.sh";
					configd:delete "/opt/vyatta/share/tmplscripts/interfaces/vti/ip/igmp/querier/querier-timeout/configd_delete.sh";
				}
			}
			leaf offlink {
				type empty;
				configd:help "Enable off-link for IGMP";
				configd:create "/opt/vyatta/share/tmplscripts/interfaces/vti/ip/igmp/offlink/configd_create.sh";
				configd:delete "/opt/vyatta/share/tmplscripts/interfaces/vti/ip/igmp/offlink/configd_delete.sh";
			}
			leaf startup-query-interval {
				type uint32 {
					range 1..18000 {
						error-message "Must be between 1-18000";
					}
				}
				configd:help "Configure a query interval value for IGMP";
				configd:update "/opt/vyatta/share/tmplscripts/interfaces/vti/ip/igmp/startup-query-interval/configd_update.sh";
				configd:delete "/opt/vyatta/share/tmplscripts/interfaces/vti/ip/igmp/startup-query-interval/configd_delete.sh";
			}
			container immediate-leave {
				presence "true";
				configd:help "Immediate leave feature";
				configd:validate "/opt/vyatta/share/tmplscripts/interfaces/vti/ip/igmp/immediate-leave/configd_validate1.cli";
				leaf group-list {
					type uint32 {
						configd:syntax "/opt/vyatta/share/tmplscripts/interfaces/vti/ip/igmp/immediate-leave/group-list/configd_syntax1.cli";
					}
					configd:help "Defines multicast groups in which the immediate leave feature is enabled";
					configd:allowed "/opt/vyatta/share/tmplscripts/interfaces/vti/ip/igmp/immediate-leave/group-list/configd_allowed.sh";
					configd:update "/opt/vyatta/share/tmplscripts/interfaces/vti/ip/igmp/immediate-leave/group-list/configd_update.sh";
					configd:delete "/opt/vyatta/share/tmplscripts/interfaces/vti/ip/igmp/immediate-leave/group-list/configd_delete.sh";
					configd:validate "/opt/vyatta/share/tmplscripts/interfaces/vti/ip/igmp/immediate-leave/group-list/configd_validate1.cli";
				}
			}
			leaf robustness-variable {
				type uint32 {
					range 2..7 {
						error-message "Must be between 2-7";
					}
				}
				configd:help "configure the robustness variable value on an interface";
				configd:update "/opt/vyatta/share/tmplscripts/interfaces/vti/ip/igmp/robustness-variable/configd_update.sh";
				configd:delete "/opt/vyatta/share/tmplscripts/interfaces/vti/ip/igmp/robustness-variable/configd_delete.sh";
			}
			leaf limit-exception {
				type uint32 {
					configd:syntax "/opt/vyatta/share/tmplscripts/interfaces/vti/ip/igmp/limit-exception/configd_syntax1.cli";
				}
				configd:help "Specify access-list that defines multicast groups that are exempted from being subject to configured limit";
				configd:allowed "/opt/vyatta/share/tmplscripts/interfaces/vti/ip/igmp/limit-exception/configd_allowed.sh";
				configd:update "/opt/vyatta/share/tmplscripts/interfaces/vti/ip/igmp/limit-exception/configd_update.sh";
				configd:delete "/opt/vyatta/share/tmplscripts/interfaces/vti/ip/igmp/limit-exception/configd_delete.sh";
				configd:validate "/opt/vyatta/share/tmplscripts/interfaces/vti/ip/igmp/limit-exception/configd_validate1.cli";
				configd:validate "/opt/vyatta/share/tmplscripts/interfaces/vti/ip/igmp/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/vti/ip/igmp/limit/configd_update.sh";
				configd:delete "/opt/vyatta/share/tmplscripts/interfaces/vti/ip/igmp/limit/configd_delete.sh";
			}
			leaf query-max-response-time {
				type uint32 {
					range 1..240 {
						error-message "Must be between 1-240";
					}
				}
				configd:help "configure the maximum response time advertised in IGMP queries";
				default "10";
				configd:validate "/opt/vyatta/share/tmplscripts/interfaces/vti/ip/igmp/query-max-response-time/configd_validate1.cli";
			}
			leaf last-member-query-count {
				type uint32 {
					range 2..7 {
						error-message "Must be between 2-7";
					}
				}
				configd:help "Set the last-member query-count value";
				configd:update "/opt/vyatta/share/tmplscripts/interfaces/vti/ip/igmp/last-member-query-count/configd_update.sh";
				configd:delete "/opt/vyatta/share/tmplscripts/interfaces/vti/ip/igmp/last-member-query-count/configd_delete.sh";
			}
			list static-group {
				configd:priority "780";
				configd:help "Set standard IP Multicast group address to be configured as a static group member";
				configd:create "/opt/vyatta/share/tmplscripts/interfaces/vti/ip/igmp/static-group/configd_create.sh";
				configd:end "/opt/vyatta/share/tmplscripts/interfaces/vti/ip/igmp/static-group/configd_end.sh";
				key "tagnode";
				leaf tagnode {
					type types:ipv4-address;
					configd:help "Set standard IP Multicast group address to be configured as a static group member";
				}
				leaf-list source {
					type string {
						configd:syntax "/opt/vyatta/share/tmplscripts/interfaces/vti/ip/igmp/static-group/source/configd_syntax1.cli";
					}
					ordered-by "user";
					configd:help "Configure standard IP source address as a static source from where multicast packets originate";
					configd:allowed "/opt/vyatta/share/tmplscripts/interfaces/vti/ip/igmp/static-group/source/configd_allowed.sh";
					configd:create "/opt/vyatta/share/tmplscripts/interfaces/vti/ip/igmp/static-group/source/configd_create.sh";
					configd:delete "/opt/vyatta/share/tmplscripts/interfaces/vti/ip/igmp/static-group/source/configd_delete.sh";
				}
			}
			list join-group {
				configd:help "Configure a join multicast group";
				configd:delete "/opt/vyatta/share/tmplscripts/interfaces/vti/ip/igmp/join-group/configd_delete.sh";
				configd:end "/opt/vyatta/share/tmplscripts/interfaces/vti/ip/igmp/join-group/configd_end.sh";
				key "tagnode";
				leaf tagnode {
					type types:ipv4-address;
					configd:help "Configure a join multicast group";
				}
				leaf source {
					type types:ipv4-address;
					configd:help "Standard IP source address to be configured as a source from where multicast packets originate";
				}
			}
			leaf last-member-query-interval {
				type uint32 {
					range 1000..25500 {
						error-message "Must be between 1000-25500";
					}
				}
				configd:help "Configure the frequency at which the router sends IGMP group-specific host query messages";
				configd:update "/opt/vyatta/share/tmplscripts/interfaces/vti/ip/igmp/last-member-query-interval/configd_update.sh";
				configd:delete "/opt/vyatta/share/tmplscripts/interfaces/vti/ip/igmp/last-member-query-interval/configd_delete.sh";
			}
			leaf version {
				type uint32 {
					range 1..3 {
						error-message "Must be between 1-3";
					}
				}
				configd:help "Configure the current IGMP protocol version on an interface";
				configd:update "/opt/vyatta/share/tmplscripts/interfaces/vti/ip/igmp/version/configd_update.sh";
				configd:delete "/opt/vyatta/share/tmplscripts/interfaces/vti/ip/igmp/version/configd_delete.sh";
			}
			leaf access-group {
				type uint32 {
					range 1..99 {
						configd:error-message "Access-list $VAR(@) doesn\'t satisfy all requirements";
					}
				}
				configd:help "Control the multicast local-membership groups learnt on an interface";
				configd:allowed "/opt/vyatta/share/tmplscripts/interfaces/vti/ip/igmp/access-group/configd_allowed.sh";
				configd:update "/opt/vyatta/share/tmplscripts/interfaces/vti/ip/igmp/access-group/configd_update.sh";
				configd:delete "/opt/vyatta/share/tmplscripts/interfaces/vti/ip/igmp/access-group/configd_delete.sh";
				configd:validate "/opt/vyatta/share/tmplscripts/interfaces/vti/ip/igmp/access-group/configd_validate1.cli";
			}
			leaf enforce-router-alert {
				type empty;
				configd:help "Enable strict RA (Router Advertisement) validation for IGMP";
				configd:create "/opt/vyatta/share/tmplscripts/interfaces/vti/ip/igmp/enforce-router-alert/configd_create.sh";
				configd:delete "/opt/vyatta/share/tmplscripts/interfaces/vti/ip/igmp/enforce-router-alert/configd_delete.sh";
			}
			leaf query-interval {
				type uint32 {
					range 2..18000 {
						error-message "Must be between 2-18000";
					}
				}
				configd:help "Configure the frequency of sending IGMP host query messages";
				default "126";
				configd:validate "/opt/vyatta/share/tmplscripts/interfaces/vti/ip/igmp/query-interval/configd_validate1.cli";
			}
			leaf startup-query-count {
				type uint32 {
					range 2..10 {
						error-message "Must be between 2-10";
					}
				}
				configd:help "Configure a startup query count for IGMP";
				configd:update "/opt/vyatta/share/tmplscripts/interfaces/vti/ip/igmp/startup-query-count/configd_update.sh";
				configd:delete "/opt/vyatta/share/tmplscripts/interfaces/vti/ip/igmp/startup-query-count/configd_delete.sh";
			}
		}
	}
}
