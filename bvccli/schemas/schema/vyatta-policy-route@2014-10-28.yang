module vyatta-policy-route {
	namespace "urn:vyatta.com:mgmt:vyatta-policy-route";
	prefix policy-route;

	import vyatta-types {
		prefix types;
	}
	import vyatta-policy {
		prefix policy;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	typedef community-list {
		type uint32 {
			range 1..199 {
				error-message "\n"
					+"  community-list must be \n"
					+"    <1-99>\tBGP community list (standard) \n"
					+"    <100-199>\tBGP community list (expanded) ";
			}
			configd:help "\n"
				+"   <1-99>\tBGP community list (standard) \n"
				+"   <100-199>\tBGP community list (expanded) ";
		}
	}

	typedef extcommunity-list {
		type uint32 {
			range 1..199 {
				error-message "\n"
				    +"  extcommunity-list must be \n"
				    +"    <1-99>\tBGP extended community list (standard) \n"
				    +"    <100-199>\tBGP extended community list (expanded) ";
			}
			configd:help "\n"
				+"   <1-99>\tBGP extended community list (standard) \n"
				+"   <100-199>\tBGP extended community list (expanded) ";
		}
	}

	augment /policy:policy {
		container route {
			configd:help "Routing policy";
			presence "true";

			list access-list6 {
				configd:priority "470";
				configd:help "IPv6 access-list filter";
				configd:end "/opt/vyatta/share/tmplscripts/policy/route/access-list6/configd_end.sh";
				key "tagnode";
				leaf tagnode {
					type string {
						pattern "[!-~]{1,64}" {
							error-message "access-list name must be 64 characters or less";
						}
						pattern "[^-].*" {
							error-message "access-list name cannot start with \"-\"";
						}
						pattern "[^\|;&$<>]*" {
							error-message "access-list name cannot contain shell punctuation";
						}
					}
					configd:help "IPv6 access-list filter";
				}
				leaf description {
					type string;
					configd:help "Description for this IPv6 access-list";
				}
				list rule {
					configd:help "Rule for this access-list6";
					key "tagnode";
					leaf tagnode {
						type uint32 {
							range 1..65535 {
								error-message "rule number must be between 1 and 65535";
							}
						}
						configd:help "Rule for this access-list6";
					}
					leaf description {
						type string;
						configd:help "Description for this IPv6 access-list rule";
					}
					leaf action {
						type enumeration {
							enum "permit" {
								configd:help "Permit matching networks";
							}
							enum "deny" {
								configd:help "Deny matching networks";
							}
						}
						configd:help "Action to take on networks matching this rule [REQUIRED]";
					}
					container source {
						presence "true";
						configd:help "Source IPv6 network to match";
						leaf exact-match {
							type empty;
							configd:help "Exact match of the network prefixes";
							configd:validate "/opt/vyatta/share/tmplscripts/policy/route/access-list6/rule/source/exact-match/configd_validate1.cli";
						}
						leaf any {
							type empty;
							configd:help "Any IPv6 address to match";
							configd:validate "/opt/vyatta/share/tmplscripts/policy/route/access-list6/rule/source/any/configd_validate1.cli";
							configd:validate "/opt/vyatta/share/tmplscripts/policy/route/access-list6/rule/source/any/configd_validate2.cli";
						}
						leaf network {
							type types:ipv6-prefix;
							configd:help "Network/netmask to match (requires inverse-mask be defined)";
							configd:validate "/opt/vyatta/share/tmplscripts/policy/route/access-list6/rule/source/network/configd_validate1.cli";
							configd:validate "/opt/vyatta/share/tmplscripts/policy/route/access-list6/rule/source/network/configd_validate2.cli";
						}
					}
				}
			}
			list access-list {
				configd:priority "470";
				configd:help "IP access-list filter";
				configd:end "/opt/vyatta/share/tmplscripts/policy/route/access-list/configd_end.sh";
				key "tagnode";
				leaf tagnode {
					type uint32 {
						configd:syntax "/opt/vyatta/share/tmplscripts/policy/route/access-list/configd_syntax1.cli";
					}
					configd:help "IP access-list filter";
				}
				leaf description {
					type string;
					configd:help "Description for this access-list";
				}
				list rule {
					configd:help "Rule for this access-list";
					key "tagnode";
					leaf tagnode {
						type uint32 {
							range 1..65535 {
								error-message "rule number must be between 1 and 65535";
							}
						}
						configd:help "Rule for this access-list";
					}
					leaf description {
						type string;
						configd:help "Description for this rule";
					}
					leaf action {
						type enumeration {
							enum "permit" {
								configd:help "Permit matching networks";
							}
							enum "deny" {
								configd:help "Deny matching networks";
							}
						}
						configd:help "Action to take on networks matching this rule [REQUIRED]";
					}
					container source {
						presence "true";
						configd:help "Source network or address to match";
						leaf host {
							type types:ipv4-address;
							configd:help "Single host IP address to match";
							configd:validate "/opt/vyatta/share/tmplscripts/policy/route/access-list/rule/source/host/configd_validate1.cli";
							configd:validate "/opt/vyatta/share/tmplscripts/policy/route/access-list/rule/source/host/configd_validate2.cli";
						}
						leaf inverse-mask {
							type types:ipv4-address;
							configd:help "Network/netmask to match (requires network be defined)";
							configd:validate "/opt/vyatta/share/tmplscripts/policy/route/access-list/rule/source/inverse-mask/configd_validate1.cli";
							configd:validate "/opt/vyatta/share/tmplscripts/policy/route/access-list/rule/source/inverse-mask/configd_validate2.cli";
							configd:validate "/opt/vyatta/share/tmplscripts/policy/route/access-list/rule/source/inverse-mask/configd_validate3.cli";
						}
						leaf any {
							type empty;
							configd:help "Any IP address to match";
							configd:validate "/opt/vyatta/share/tmplscripts/policy/route/access-list/rule/source/any/configd_validate1.cli";
							configd:validate "/opt/vyatta/share/tmplscripts/policy/route/access-list/rule/source/any/configd_validate2.cli";
						}
						leaf network {
							type types:ipv4-address;
							configd:help "Network/netmask to match (requires inverse-mask be defined)";
							configd:validate "/opt/vyatta/share/tmplscripts/policy/route/access-list/rule/source/network/configd_validate1.cli";
							configd:validate "/opt/vyatta/share/tmplscripts/policy/route/access-list/rule/source/network/configd_validate2.cli";
							configd:validate "/opt/vyatta/share/tmplscripts/policy/route/access-list/rule/source/network/configd_validate3.cli";
						}
					}
					container destination {
						presence "true";
						configd:help "Destination network or address";
						leaf host {
							type types:ipv4-address;
							configd:help "Single host IP address to match";
							configd:validate "/opt/vyatta/share/tmplscripts/policy/route/access-list/rule/destination/host/configd_validate1.cli";
							configd:validate "/opt/vyatta/share/tmplscripts/policy/route/access-list/rule/destination/host/configd_validate2.cli";
							configd:validate "/opt/vyatta/share/tmplscripts/policy/route/access-list/rule/destination/host/configd_validate3.cli";
						}
						leaf inverse-mask {
							type types:ipv4-address;
							configd:help "Network/netmask to match (requires network be defined)";
							configd:validate "/opt/vyatta/share/tmplscripts/policy/route/access-list/rule/destination/inverse-mask/configd_validate1.cli";
							configd:validate "/opt/vyatta/share/tmplscripts/policy/route/access-list/rule/destination/inverse-mask/configd_validate2.cli";
							configd:validate "/opt/vyatta/share/tmplscripts/policy/route/access-list/rule/destination/inverse-mask/configd_validate3.cli";
							configd:validate "/opt/vyatta/share/tmplscripts/policy/route/access-list/rule/destination/inverse-mask/configd_validate4.cli";
						}
						leaf any {
							type empty;
							configd:help "Any IP address to match";
							configd:validate "/opt/vyatta/share/tmplscripts/policy/route/access-list/rule/destination/any/configd_validate1.cli";
							configd:validate "/opt/vyatta/share/tmplscripts/policy/route/access-list/rule/destination/any/configd_validate2.cli";
							configd:validate "/opt/vyatta/share/tmplscripts/policy/route/access-list/rule/destination/any/configd_validate3.cli";
						}
						leaf network {
							type types:ipv4-address;
							configd:help "Network/netmask to match (requires inverse-mask be defined)";
							configd:validate "/opt/vyatta/share/tmplscripts/policy/route/access-list/rule/destination/network/configd_validate1.cli";
							configd:validate "/opt/vyatta/share/tmplscripts/policy/route/access-list/rule/destination/network/configd_validate2.cli";
							configd:validate "/opt/vyatta/share/tmplscripts/policy/route/access-list/rule/destination/network/configd_validate3.cli";
							configd:validate "/opt/vyatta/share/tmplscripts/policy/route/access-list/rule/destination/network/configd_validate4.cli";
						}
					}
				}
			}
			list community-list {
				configd:priority "470";
				configd:help "Border Gateway Protocol (BGP) community-list filter";
				configd:end "/opt/vyatta/share/tmplscripts/policy/route/community-list/configd_end.sh";
				key "tagnode";
				leaf tagnode {
					type community-list;
				}
				leaf description {
					type string;
					configd:help "Description for this community list";
				}
				list rule {
					configd:help "create a rule for this BGP community list";
					key "tagnode";
					leaf tagnode {
						type uint32 {
							range 1..65535 {
								error-message "rule number must be between 1 and 65535";
							}
						}
						configd:help "create a rule for this BGP community list";
					}
					leaf description {
						type string;
						configd:help "Description for this rule";
					}
					leaf action {
						type enumeration {
							enum "permit" {
								configd:help "Permit matching communities";
							}
							enum "deny" {
								configd:help "Deny matching communities";
							}
						}
						configd:help "Action to take on communities matching this rule [REQUIRED]";
					}
					leaf community {
						type string {
							configd:syntax "/opt/vyatta/share/tmplscripts/policy/route/community-list/rule/community/configd_syntax1.cli";
						}
						configd:help "Border Gateway Protocl (BGP) community attribute";
						configd:allowed "/opt/vyatta/share/tmplscripts/policy/route/community-list/rule/community/configd_allowed.sh";
						configd:validate "/opt/vyatta/share/tmplscripts/policy/route/community-list/rule/community/configd_validate1.cli";
					}
					leaf regex {
						type string {
							configd:syntax "/opt/vyatta/share/tmplscripts/policy/route/community-list/rule/regex/configd_syntax1.cli";
						}
						configd:help "Regular expression to match against a community list";
						configd:validate "/opt/vyatta/share/tmplscripts/policy/route/community-list/rule/regex/configd_validate1.cli";
					}
				}
			}
			list extcommunity-list {
				configd:priority "470";
				configd:help "Border Gateway Protocol (BGP) extended community-list filter";
				configd:end "/opt/vyatta/share/tmplscripts/policy/route/extcommunity-list/configd_end.sh";
				key "tagnode";
				leaf tagnode {
					type extcommunity-list;
				}
				leaf description {
					type string;
					configd:help "Description for this extended community list";
				}
				list rule {
					configd:help "create a rule for this BGP extended community list";
					key "tagnode";
					leaf tagnode {
						type uint32 {
							range 1..65535 {
								error-message "rule number must be between 1 and 65535";
							}
						}
						configd:help "create a rule for this BGP extended community list";
					}
					leaf description {
						type string;
						configd:help "Description for this rule";
					}
					leaf action {
						type enumeration {
							enum "permit" {
								configd:help "Permit matching communities";
							}
							enum "deny" {
								configd:help "Deny matching communities";
							}
						}
						configd:help "Action to take on communities matching this rule [REQUIRED]";
					}
					leaf rt {
						type string {
							configd:syntax "/opt/vyatta/share/tmplscripts/policy/route/extcommunity-list/rule/rt/rt_check.cli";
						}
						configd:help "Route Target extended community in AA:NN or IPAddr:NN format";
						configd:validate "/opt/vyatta/share/tmplscripts/policy/route/extcommunity-list/rule/rt/configd_validate1.cli";
					}
					leaf soo {
						type string {
							configd:syntax "/opt/vyatta/share/tmplscripts/policy/route/extcommunity-list/rule/soo/soo_check.cli";
						}
						configd:help "Site-of-Origin extended community in AA:NN or IPAddr:NN format";
						configd:validate "/opt/vyatta/share/tmplscripts/policy/route/extcommunity-list/rule/soo/configd_validate1.cli";
					}
                    leaf regex {
                        type string {
                            configd:syntax "/opt/vyatta/share/tmplscripts/policy/route/extcommunity-list/rule/regex/listnum_check.cli";
                        }
                        configd:help "Regular expression to match against a extcommunity list";
                        configd:validate "/opt/vyatta/share/tmplscripts/policy/route/extcommunity-list/rule/regex/configd_validate1.cli";
                    }
				}
			}
			list as-path-list {
				configd:priority "470";
				configd:help "Border Gateway Protocol (BGP) autonomous system path filter";
				configd:end "/opt/vyatta/share/tmplscripts/policy/route/as-path-list/configd_end.sh";
				key "tagnode";
				leaf tagnode {
					type string {
						pattern "[-a-zA-Z0-9.]+" {
							error-message "as-path-list name must be alpha-numeric";
						}
					}
					configd:help "Border Gateway Protocol (BGP) autonomous system path filter";
				}
				leaf description {
					type string;
					configd:help "Description for this as-path-list";
				}
				list rule {
					configd:help "Rule for this as-path-list";
					key "tagnode";
					leaf tagnode {
						type uint32 {
							range 1..65535 {
								error-message "rule number must be between 1 and 65535";
							}
						}
						configd:help "Rule for this as-path-list";
					}
					leaf description {
						type string;
						configd:help "Description for this rule";
					}
					leaf action {
						type enumeration {
							enum "permit" {
								configd:help "Permit matching as-paths";
							}
							enum "deny" {
								configd:help "Deny matching as-paths";
							}
						}
						configd:help "Action to take on AS paths matching this rule [REQUIRED]";
					}
					leaf regex {
						type string;
						configd:help "Regular expression to match against an AS path";
						configd:validate "/opt/vyatta/share/tmplscripts/policy/route/as-path-list/rule/regex/configd_validate1.cli";
					}
				}
			}
			list route-map {
				configd:priority "470";
				configd:help "IP route-map";
				key "tagnode";
				leaf tagnode {
					type string {
						pattern "[-a-zA-Z0-9.]+" {
							configd:error-message "route-map $VAR(@): name must be alpha-numeric";
						}
					}
					configd:help "IP route-map";
				}
				leaf description {
					type string;
					configd:help "Description for this route-map";
				}
				list rule {
					configd:help "Rule for this route-map";
					configd:delete "/opt/vyatta/share/tmplscripts/policy/route/route-map/rule/configd_delete.sh";
					key "tagnode";
					leaf tagnode {
						type uint32 {
							range 1..65535 {
								error-message "rule number must be between 1 and 65535";
							}
						}
						configd:help "Rule for this route-map";
					}
					leaf description {
						type string;
						configd:help "Description for this rule";
					}
					leaf action {
						type enumeration {
							enum "permit" {
								configd:help "Permit matching prefixes";
							}
							enum "deny" {
								configd:help "Deny matching prefixes";
							}
						}
						configd:help "Action to take on prefixes matching this rule [REQUIRED]";
						configd:update "/opt/vyatta/share/tmplscripts/policy/route/route-map/rule/action/configd_update.sh";
						configd:delete "/opt/vyatta/share/tmplscripts/policy/route/route-map/rule/action/configd_delete.sh";
					}
					container set {
						presence "true";
						configd:help "Route parameters";
						leaf tag {
							type uint32 {
								range 1..65535 {
									error-message "tag must be between 1 and 65535";
								}
							}
							configd:help "Tag value for routing protocol";
							configd:update "/opt/vyatta/share/tmplscripts/policy/route/route-map/rule/set/tag/configd_update.sh";
							configd:delete "/opt/vyatta/share/tmplscripts/policy/route/route-map/rule/set/tag/configd_delete.sh";
							configd:validate "/opt/vyatta/share/tmplscripts/policy/route/route-map/rule/set/tag/configd_validate1.cli";
						}
						leaf originator-id {
							type types:ipv4-address;
							configd:help "Border Gateway Protocol (BGP) originator ID attribute";
							configd:update "/opt/vyatta/share/tmplscripts/policy/route/route-map/rule/set/originator-id/configd_update.sh";
							configd:delete "/opt/vyatta/share/tmplscripts/policy/route/route-map/rule/set/originator-id/configd_delete.sh";
							configd:validate "/opt/vyatta/share/tmplscripts/policy/route/route-map/rule/set/originator-id/configd_validate1.cli";
						}
						container aggregator {
							presence "true";
							configd:help "Border Gateway Protocol (BGP) aggregator attribute";
							configd:end "/opt/vyatta/share/tmplscripts/policy/route/route-map/rule/set/aggregator/configd_end.sh";
							configd:validate "/opt/vyatta/share/tmplscripts/policy/route/route-map/rule/set/aggregator/configd_validate1.cli";
							configd:validate "/opt/vyatta/share/tmplscripts/policy/route/route-map/rule/set/aggregator/configd_validate2.cli";
							leaf ip {
								type types:ipv4-address;
								configd:help "IP address of an aggregation";
							}
							leaf as {
								type uint32 {
									range 1..max {
										error-message "BGP AS number must be between 1 and 4294967295";
									}
								}
								configd:help "AS number of an aggregation";
							}
						}
						leaf local-preference {
							type uint32;
							configd:help "Border Gateway Protocol (BGP) local preference attribute";
							configd:update "/opt/vyatta/share/tmplscripts/policy/route/route-map/rule/set/local-preference/configd_update.sh";
							configd:delete "/opt/vyatta/share/tmplscripts/policy/route/route-map/rule/set/local-preference/configd_delete.sh";
							configd:validate "/opt/vyatta/share/tmplscripts/policy/route/route-map/rule/set/local-preference/configd_validate1.cli";
						}
						container ipv6-next-hop {
							presence "true";
							configd:help "Nexthop IPv6 address";
							leaf global {
								type types:ipv6-address;
								configd:help "Nexthop IPv6 global address";
								configd:update "/opt/vyatta/share/tmplscripts/policy/route/route-map/rule/set/ipv6-next-hop/global/configd_update.sh";
								configd:delete "/opt/vyatta/share/tmplscripts/policy/route/route-map/rule/set/ipv6-next-hop/global/configd_delete.sh";
								configd:validate "/opt/vyatta/share/tmplscripts/policy/route/route-map/rule/set/ipv6-next-hop/global/configd_validate1.cli";
							}
							leaf local {
								type types:ipv6-address;
								configd:help "Nexthop IPv6 local address";
								configd:update "/opt/vyatta/share/tmplscripts/policy/route/route-map/rule/set/ipv6-next-hop/local/configd_update.sh";
								configd:delete "/opt/vyatta/share/tmplscripts/policy/route/route-map/rule/set/ipv6-next-hop/local/configd_delete.sh";
								configd:validate "/opt/vyatta/share/tmplscripts/policy/route/route-map/rule/set/ipv6-next-hop/local/configd_validate1.cli";
							}
						}
						leaf origin {
							type enumeration {
								enum "igp" {
									configd:help "Interior gateway protocol origin";
								}
								enum "egp" {
									configd:help "Exterior gateway protocol origin";
								}
								enum "incomplete" {
									configd:help "Incomplete origin";
								}
							}
							configd:help "Border Gateway Protocl (BGP) origin code";
							configd:allowed "/opt/vyatta/share/tmplscripts/policy/route/route-map/rule/set/origin/configd_allowed.sh";
							configd:update "/opt/vyatta/share/tmplscripts/policy/route/route-map/rule/set/origin/configd_update.sh";
							configd:delete "/opt/vyatta/share/tmplscripts/policy/route/route-map/rule/set/origin/configd_delete.sh";
							configd:validate "/opt/vyatta/share/tmplscripts/policy/route/route-map/rule/set/origin/configd_validate1.cli";
						}
						leaf metric-type {
							type enumeration {
								enum "type-1" {
									configd:help "OSPF external type 1 metric";
								}
								enum "type-2" {
									configd:help "OSPF external type 2 metric";
								}
							}
							configd:help "Open Shortest Path First (OSPF) external metric-type";
							configd:update "/opt/vyatta/share/tmplscripts/policy/route/route-map/rule/set/metric-type/configd_update.sh";
							configd:delete "/opt/vyatta/share/tmplscripts/policy/route/route-map/rule/set/metric-type/configd_delete.sh";
							configd:validate "/opt/vyatta/share/tmplscripts/policy/route/route-map/rule/set/metric-type/configd_validate1.cli";
						}
						leaf as-path-prepend {
							type string {
								configd:syntax "/opt/vyatta/share/tmplscripts/policy/route/route-map/rule/set/as-path-prepend/configd_syntax1.cli";
							}
							configd:help "Prepend string for a Border Gateway Protocol (BGP) AS-path attribute";
							configd:update "/opt/vyatta/share/tmplscripts/policy/route/route-map/rule/set/as-path-prepend/configd_update.sh";
							configd:delete "/opt/vyatta/share/tmplscripts/policy/route/route-map/rule/set/as-path-prepend/configd_delete.sh";
							configd:validate "/opt/vyatta/share/tmplscripts/policy/route/route-map/rule/set/as-path-prepend/configd_validate1.cli";
						}
						leaf community {
							type string {
								configd:syntax "/opt/vyatta/share/tmplscripts/policy/route/route-map/rule/set/community/configd_syntax1.cli";
							}
							configd:help "Border Gateway Protocl (BGP) community attribute";
							configd:allowed "/opt/vyatta/share/tmplscripts/policy/route/route-map/rule/set/community/configd_allowed.sh";
							configd:update "/opt/vyatta/share/tmplscripts/policy/route/route-map/rule/set/community/configd_update.sh";
							configd:delete "/opt/vyatta/share/tmplscripts/policy/route/route-map/rule/set/community/configd_delete.sh";
							configd:validate "/opt/vyatta/share/tmplscripts/policy/route/route-map/rule/set/community/configd_validate1.cli";
						}
						container extcommunity {
							presence "true";
							configd:help "Border Gateway Protocl (BGP) extcommunity attribute";
					        leaf rt {
					        	type string;
					        	configd:help "Route Target extended community in AA:NN or IPAddr:NN format";
					        	configd:validate "/opt/vyatta/share/tmplscripts/policy/route/route-map/rule/set/extcommunity/rt/configd_validate1.cli";
							    configd:update "/opt/vyatta/share/tmplscripts/policy/route/route-map/rule/set/extcommunity/rt/configd_update.sh";
					        }
					        leaf soo {
					        	type string;
					        	configd:help "Site-of-Origin extended community in AA:NN or IPAddr:NN format";
					        	configd:validate "/opt/vyatta/share/tmplscripts/policy/route/route-map/rule/set/extcommunity/soo/configd_validate1.cli";
							    configd:update "/opt/vyatta/share/tmplscripts/policy/route/route-map/rule/set/extcommunity/soo/configd_update.sh";
					        }
						}
						leaf delete-community {
							type uint32;
							configd:help "Border Gateway Protocol (BGP) communities to delete";
							configd:update "/opt/vyatta/share/tmplscripts/policy/route/route-map/rule/set/delete-community/configd_update.sh";
							configd:delete "/opt/vyatta/share/tmplscripts/policy/route/route-map/rule/set/delete-community/configd_delete.sh";
							configd:validate "/opt/vyatta/share/tmplscripts/policy/route/route-map/rule/set/delete-community/configd_validate1.cli";
						}
						leaf atomic-aggregate {
							type empty;
							configd:help "Border Gateway Protocol (BGP) atomic aggregate attribute";
							configd:update "/opt/vyatta/share/tmplscripts/policy/route/route-map/rule/set/atomic-aggregate/configd_update.sh";
							configd:delete "/opt/vyatta/share/tmplscripts/policy/route/route-map/rule/set/atomic-aggregate/configd_delete.sh";
							configd:validate "/opt/vyatta/share/tmplscripts/policy/route/route-map/rule/set/atomic-aggregate/configd_validate1.cli";
						}
						leaf weight {
							type uint32;
							configd:help "Border Gateway Protocol (BGP) weight attribute";
							configd:update "/opt/vyatta/share/tmplscripts/policy/route/route-map/rule/set/weight/configd_update.sh";
							configd:delete "/opt/vyatta/share/tmplscripts/policy/route/route-map/rule/set/weight/configd_delete.sh";
							configd:validate "/opt/vyatta/share/tmplscripts/policy/route/route-map/rule/set/weight/configd_validate1.cli";
						}
						leaf metric {
							type string {
								configd:syntax "/opt/vyatta/share/tmplscripts/policy/route/route-map/rule/set/metric/configd_syntax1.cli";
							}
							configd:help "Destination routing protocol metric";
							configd:update "/opt/vyatta/share/tmplscripts/policy/route/route-map/rule/set/metric/configd_update.sh";
							configd:delete "/opt/vyatta/share/tmplscripts/policy/route/route-map/rule/set/metric/configd_delete.sh";
							configd:validate "/opt/vyatta/share/tmplscripts/policy/route/route-map/rule/set/metric/configd_validate1.cli";
						}
						leaf ip-next-hop {
							type types:ipv4-address;
							configd:help "Nexthop IP address";
							configd:update "/opt/vyatta/share/tmplscripts/policy/route/route-map/rule/set/ip-next-hop/configd_update.sh";
							configd:delete "/opt/vyatta/share/tmplscripts/policy/route/route-map/rule/set/ip-next-hop/configd_delete.sh";
							configd:validate "/opt/vyatta/share/tmplscripts/policy/route/route-map/rule/set/ip-next-hop/configd_validate1.cli";
						}
					}
					leaf continue {
						type uint32 {
							range 1..65535 {
								error-message "continue must be between 1 and 65535";
							}
						}
						configd:help "Jump to a different rule in this route-map on a match";
						configd:update "/opt/vyatta/share/tmplscripts/policy/route/route-map/rule/continue/configd_update.sh";
						configd:delete "/opt/vyatta/share/tmplscripts/policy/route/route-map/rule/continue/configd_delete.sh";
						configd:validate "/opt/vyatta/share/tmplscripts/policy/route/route-map/rule/continue/configd_validate1.cli";
						configd:validate "/opt/vyatta/share/tmplscripts/policy/route/route-map/rule/continue/configd_validate2.cli";
					}
					container match {
						presence "true";
						configd:help "Route parameters to match";
						leaf tag {
							type uint32 {
								range 1..65535 {
									error-message "tag must be between 1 and 65535";
								}
							}
							configd:help "Route tag to match";
							configd:update "/opt/vyatta/share/tmplscripts/policy/route/route-map/rule/match/tag/configd_update.sh";
							configd:delete "/opt/vyatta/share/tmplscripts/policy/route/route-map/rule/match/tag/configd_delete.sh";
							configd:validate "/opt/vyatta/share/tmplscripts/policy/route/route-map/rule/match/tag/configd_validate1.cli";
						}
						container ip {
							presence "true";
							configd:help "IP prefix parameters to match";
							container peer {
								presence "true";
								configd:help "IP peer to match";
								leaf access-list {
									type uint32;
									configd:help "IP access-list to match";
									configd:update "/opt/vyatta/share/tmplscripts/policy/route/route-map/rule/match/ip/peer/access-list/configd_update.sh";
									configd:delete "/opt/vyatta/share/tmplscripts/policy/route/route-map/rule/match/ip/peer/access-list/configd_delete.sh";
									configd:validate "/opt/vyatta/share/tmplscripts/policy/route/route-map/rule/match/ip/peer/access-list/configd_validate1.cli";
									configd:validate "/opt/vyatta/share/tmplscripts/policy/route/route-map/rule/match/ip/peer/access-list/configd_validate2.cli";
									configd:validate "/opt/vyatta/share/tmplscripts/policy/route/route-map/rule/match/ip/peer/access-list/configd_validate3.cli";
								}
								leaf prefix-list {
									type string;
									configd:help "IP prefix-list to match";
									configd:update "/opt/vyatta/share/tmplscripts/policy/route/route-map/rule/match/ip/peer/prefix-list/configd_update.sh";
									configd:delete "/opt/vyatta/share/tmplscripts/policy/route/route-map/rule/match/ip/peer/prefix-list/configd_delete.sh";
									configd:validate "/opt/vyatta/share/tmplscripts/policy/route/route-map/rule/match/ip/peer/prefix-list/configd_validate1.cli";
									configd:validate "/opt/vyatta/share/tmplscripts/policy/route/route-map/rule/match/ip/peer/prefix-list/configd_validate2.cli";
									configd:validate "/opt/vyatta/share/tmplscripts/policy/route/route-map/rule/match/ip/peer/prefix-list/configd_validate3.cli";
								}
							}
							container nexthop {
								presence "true";
								configd:help "IP next-hop of route to match";
								leaf access-list {
									type uint32;
									configd:help "IP access-list to match";
									configd:update "/opt/vyatta/share/tmplscripts/policy/route/route-map/rule/match/ip/nexthop/access-list/configd_update.sh";
									configd:delete "/opt/vyatta/share/tmplscripts/policy/route/route-map/rule/match/ip/nexthop/access-list/configd_delete.sh";
									configd:validate "/opt/vyatta/share/tmplscripts/policy/route/route-map/rule/match/ip/nexthop/access-list/configd_validate1.cli";
									configd:validate "/opt/vyatta/share/tmplscripts/policy/route/route-map/rule/match/ip/nexthop/access-list/configd_validate2.cli";
									configd:validate "/opt/vyatta/share/tmplscripts/policy/route/route-map/rule/match/ip/nexthop/access-list/configd_validate3.cli";
								}
								leaf prefix-list {
									type string;
									configd:help "IP prefix-list to match";
									configd:update "/opt/vyatta/share/tmplscripts/policy/route/route-map/rule/match/ip/nexthop/prefix-list/configd_update.sh";
									configd:delete "/opt/vyatta/share/tmplscripts/policy/route/route-map/rule/match/ip/nexthop/prefix-list/configd_delete.sh";
									configd:validate "/opt/vyatta/share/tmplscripts/policy/route/route-map/rule/match/ip/nexthop/prefix-list/configd_validate1.cli";
									configd:validate "/opt/vyatta/share/tmplscripts/policy/route/route-map/rule/match/ip/nexthop/prefix-list/configd_validate2.cli";
									configd:validate "/opt/vyatta/share/tmplscripts/policy/route/route-map/rule/match/ip/nexthop/prefix-list/configd_validate3.cli";
								}
							}
							container address {
								presence "true";
								configd:help "IP address of route to match";
								leaf access-list {
									type uint32;
									configd:help "IP access-list to match";
									configd:allowed "/opt/vyatta/share/tmplscripts/policy/route/route-map/rule/match/ip/address/access-list/configd_allowed.sh";
									configd:update "/opt/vyatta/share/tmplscripts/policy/route/route-map/rule/match/ip/address/access-list/configd_update.sh";
									configd:delete "/opt/vyatta/share/tmplscripts/policy/route/route-map/rule/match/ip/address/access-list/configd_delete.sh";
									configd:validate "/opt/vyatta/share/tmplscripts/policy/route/route-map/rule/match/ip/address/access-list/configd_validate1.cli";
									configd:validate "/opt/vyatta/share/tmplscripts/policy/route/route-map/rule/match/ip/address/access-list/configd_validate2.cli";
									configd:validate "/opt/vyatta/share/tmplscripts/policy/route/route-map/rule/match/ip/address/access-list/configd_validate3.cli";
								}
								leaf prefix-list {
									type string;
									configd:help "IP prefix-list to match";
									configd:allowed "/opt/vyatta/share/tmplscripts/policy/route/route-map/rule/match/ip/address/prefix-list/configd_allowed.sh";
									configd:update "/opt/vyatta/share/tmplscripts/policy/route/route-map/rule/match/ip/address/prefix-list/configd_update.sh";
									configd:delete "/opt/vyatta/share/tmplscripts/policy/route/route-map/rule/match/ip/address/prefix-list/configd_delete.sh";
									configd:validate "/opt/vyatta/share/tmplscripts/policy/route/route-map/rule/match/ip/address/prefix-list/configd_validate1.cli";
									configd:validate "/opt/vyatta/share/tmplscripts/policy/route/route-map/rule/match/ip/address/prefix-list/configd_validate2.cli";
									configd:validate "/opt/vyatta/share/tmplscripts/policy/route/route-map/rule/match/ip/address/prefix-list/configd_validate3.cli";
								}
							}
						}
						leaf origin {
							type enumeration {
								enum "egp" {
									configd:help "Exterior gateway protocol origin ";
								}
								enum "igp" {
									configd:help "Interior gateway protocol origin";
								}
								enum "incomplete" {
									configd:help "Incomplete origin ";
								}
							}
							configd:help "Border Gateway Protocol (BGP) origin code to match";
							configd:update "/opt/vyatta/share/tmplscripts/policy/route/route-map/rule/match/origin/configd_update.sh";
							configd:delete "/opt/vyatta/share/tmplscripts/policy/route/route-map/rule/match/origin/configd_delete.sh";
							configd:validate "/opt/vyatta/share/tmplscripts/policy/route/route-map/rule/match/origin/configd_validate1.cli";
						}
						leaf interface {
							type string;
							configd:help "First hop interface of a route to match";
							configd:update "/opt/vyatta/share/tmplscripts/policy/route/route-map/rule/match/interface/configd_update.sh";
							configd:delete "/opt/vyatta/share/tmplscripts/policy/route/route-map/rule/match/interface/configd_delete.sh";
							configd:validate "/opt/vyatta/share/tmplscripts/policy/route/route-map/rule/match/interface/configd_validate1.cli";
							configd:validate "/opt/vyatta/share/tmplscripts/policy/route/route-map/rule/match/interface/configd_validate2.cli";
						}
						container community {
							presence "true";
							configd:help "BGP community-list to match";
							configd:end "/opt/vyatta/share/tmplscripts/policy/route/route-map/rule/match/community/configd_end.sh";
							leaf exact-match {
								type empty;
								configd:help "Community-list to exactly match";
							}
							leaf community-list {
								type community-list;
								configd:help "BGP community-list to match";
								configd:validate "/opt/vyatta/share/tmplscripts/policy/route/route-map/rule/match/community/community-list/configd_validate1.cli";
							}
						}
						container extcommunity {
							presence "true";
							configd:help "BGP extcommunity-list to match";
							configd:end "/opt/vyatta/share/tmplscripts/policy/route/route-map/rule/match/extcommunity/configd_end.sh";
							leaf exact-match {
								type empty;
								configd:help "Extcommunity-list to exactly match";
							}
							leaf extcommunity-list {
								type extcommunity-list;
								configd:help "BGP extcommunity-list to match";
								configd:validate "/opt/vyatta/share/tmplscripts/policy/route/route-map/rule/match/extcommunity/extcommunity-list/configd_validate1.cli";
							}
						}
						container ipv6 {
							presence "true";
							configd:help "IPv6 prefix parameters to match";
							container peer {
								presence "true";
								configd:help "IP peer to match";
								leaf access-list {
									type string;
									configd:help "IPv6 access-list6 to match";
									configd:update "/opt/vyatta/share/tmplscripts/policy/route/route-map/rule/match/ipv6/peer/access-list/configd_update.sh";
									configd:delete "/opt/vyatta/share/tmplscripts/policy/route/route-map/rule/match/ipv6/peer/access-list/configd_delete.sh";
									configd:validate "/opt/vyatta/share/tmplscripts/policy/route/route-map/rule/match/ipv6/peer/access-list/configd_validate1.cli";
									configd:validate "/opt/vyatta/share/tmplscripts/policy/route/route-map/rule/match/ipv6/peer/access-list/configd_validate2.cli";
									configd:validate "/opt/vyatta/share/tmplscripts/policy/route/route-map/rule/match/ipv6/peer/access-list/configd_validate3.cli";
								}
								leaf prefix-list {
									type string;
									configd:help "IPv6 prefix-list to match";
									configd:update "/opt/vyatta/share/tmplscripts/policy/route/route-map/rule/match/ipv6/peer/prefix-list/configd_update.sh";
									configd:delete "/opt/vyatta/share/tmplscripts/policy/route/route-map/rule/match/ipv6/peer/prefix-list/configd_delete.sh";
									configd:validate "/opt/vyatta/share/tmplscripts/policy/route/route-map/rule/match/ipv6/peer/prefix-list/configd_validate1.cli";
									configd:validate "/opt/vyatta/share/tmplscripts/policy/route/route-map/rule/match/ipv6/peer/prefix-list/configd_validate2.cli";
									configd:validate "/opt/vyatta/share/tmplscripts/policy/route/route-map/rule/match/ipv6/peer/prefix-list/configd_validate3.cli";
								}
							}
							container nexthop {
								presence "true";
								configd:help "IP next-hop of route to match";
								leaf access-list {
									type string;
									configd:help "IPv6 access-list6 to match";
									configd:update "/opt/vyatta/share/tmplscripts/policy/route/route-map/rule/match/ipv6/nexthop/access-list/configd_update.sh";
									configd:delete "/opt/vyatta/share/tmplscripts/policy/route/route-map/rule/match/ipv6/nexthop/access-list/configd_delete.sh";
									configd:validate "/opt/vyatta/share/tmplscripts/policy/route/route-map/rule/match/ipv6/nexthop/access-list/configd_validate1.cli";
									configd:validate "/opt/vyatta/share/tmplscripts/policy/route/route-map/rule/match/ipv6/nexthop/access-list/configd_validate2.cli";
									configd:validate "/opt/vyatta/share/tmplscripts/policy/route/route-map/rule/match/ipv6/nexthop/access-list/configd_validate3.cli";
								}
								leaf prefix-list {
									type string;
									configd:help "IPv6 prefix-list to match";
									configd:update "/opt/vyatta/share/tmplscripts/policy/route/route-map/rule/match/ipv6/nexthop/prefix-list/configd_update.sh";
									configd:delete "/opt/vyatta/share/tmplscripts/policy/route/route-map/rule/match/ipv6/nexthop/prefix-list/configd_delete.sh";
									configd:validate "/opt/vyatta/share/tmplscripts/policy/route/route-map/rule/match/ipv6/nexthop/prefix-list/configd_validate1.cli";
									configd:validate "/opt/vyatta/share/tmplscripts/policy/route/route-map/rule/match/ipv6/nexthop/prefix-list/configd_validate2.cli";
									configd:validate "/opt/vyatta/share/tmplscripts/policy/route/route-map/rule/match/ipv6/nexthop/prefix-list/configd_validate3.cli";
								}
							}
							container address {
								presence "true";
								configd:help "IPv6 address of route to match";
								leaf access-list {
									type string;
									configd:help "IPv6 access-list6 to match";
									configd:allowed "/opt/vyatta/share/tmplscripts/policy/route/route-map/rule/match/ipv6/address/access-list/configd_allowed.sh";
									configd:update "/opt/vyatta/share/tmplscripts/policy/route/route-map/rule/match/ipv6/address/access-list/configd_update.sh";
									configd:delete "/opt/vyatta/share/tmplscripts/policy/route/route-map/rule/match/ipv6/address/access-list/configd_delete.sh";
									configd:validate "/opt/vyatta/share/tmplscripts/policy/route/route-map/rule/match/ipv6/address/access-list/configd_validate1.cli";
									configd:validate "/opt/vyatta/share/tmplscripts/policy/route/route-map/rule/match/ipv6/address/access-list/configd_validate2.cli";
									configd:validate "/opt/vyatta/share/tmplscripts/policy/route/route-map/rule/match/ipv6/address/access-list/configd_validate3.cli";
								}
								leaf prefix-list {
									type string;
									configd:help "IPv6 prefix-list to match";
									configd:allowed "/opt/vyatta/share/tmplscripts/policy/route/route-map/rule/match/ipv6/address/prefix-list/configd_allowed.sh";
									configd:update "/opt/vyatta/share/tmplscripts/policy/route/route-map/rule/match/ipv6/address/prefix-list/configd_update.sh";
									configd:delete "/opt/vyatta/share/tmplscripts/policy/route/route-map/rule/match/ipv6/address/prefix-list/configd_delete.sh";
									configd:validate "/opt/vyatta/share/tmplscripts/policy/route/route-map/rule/match/ipv6/address/prefix-list/configd_validate1.cli";
									configd:validate "/opt/vyatta/share/tmplscripts/policy/route/route-map/rule/match/ipv6/address/prefix-list/configd_validate2.cli";
									configd:validate "/opt/vyatta/share/tmplscripts/policy/route/route-map/rule/match/ipv6/address/prefix-list/configd_validate3.cli";
								}
							}
						}
						leaf as-path {
							type string;
							configd:help "BGP as-path-list to match";
							configd:update "/opt/vyatta/share/tmplscripts/policy/route/route-map/rule/match/as-path/configd_update.sh";
							configd:delete "/opt/vyatta/share/tmplscripts/policy/route/route-map/rule/match/as-path/configd_delete.sh";
							configd:validate "/opt/vyatta/share/tmplscripts/policy/route/route-map/rule/match/as-path/configd_validate1.cli";
							configd:validate "/opt/vyatta/share/tmplscripts/policy/route/route-map/rule/match/as-path/configd_validate2.cli";
						}
						leaf metric {
							type uint32 {
								range 1..65535 {
									error-message "metric must be between 1 and 65535";
								}
							}
							configd:help "Metric of route to match";
							configd:update "/opt/vyatta/share/tmplscripts/policy/route/route-map/rule/match/metric/configd_update.sh";
							configd:delete "/opt/vyatta/share/tmplscripts/policy/route/route-map/rule/match/metric/configd_delete.sh";
							configd:validate "/opt/vyatta/share/tmplscripts/policy/route/route-map/rule/match/metric/configd_validate1.cli";
						}
					}
				}
			}
			list prefix-list6 {
				configd:priority "470";
				configd:help "IPv6 prefix-list filter";
				key "tagnode";
				leaf tagnode {
					type string {
						pattern "[-a-zA-Z0-9.]+" {
							error-message "prefix-list6 name must be alpha-numeric";
						}
					}
					configd:help "IPv6 prefix-list filter";
				}
				leaf description {
					type string;
					configd:help "Description for this prefix-list6";
				}
				list rule {
					configd:help "Rule for this prefix-list6";
					configd:delete "/opt/vyatta/share/tmplscripts/policy/route/prefix-list6/rule/configd_delete.sh";
					configd:end "/opt/vyatta/share/tmplscripts/policy/route/prefix-list6/rule/configd_end.sh";
					configd:validate "/opt/vyatta/share/tmplscripts/policy/route/prefix-list6/rule/configd_validate1.cli";
					configd:validate "/opt/vyatta/share/tmplscripts/policy/route/prefix-list6/rule/configd_validate2.cli";
					key "tagnode";
					leaf tagnode {
						type uint32 {
							range 1..65535 {
								error-message "rule number must be between 1 and 65535";
							}
						}
						configd:help "Rule for this prefix-list6";
					}
					leaf description {
						type string;
						configd:help "Description for this rule";
					}
					leaf action {
						type enumeration {
							enum "permit" {
								configd:help "Permit matching prefixes";
							}
							enum "deny" {
								configd:help "Deny matching prefixes";
							}
						}
						configd:help "Action to take on prefixes matching this rule";
					}
					leaf ge {
						type uint32 {
							range 0..128 {
								error-message "ge must be between 0 and 128";
							}
						}
						configd:help "Prefix length to match a netmask greater than or equal to it";
					}
					leaf prefix {
						type types:ipv6-prefix;
						configd:help "Prefix to match";
					}
					leaf le {
						type uint32 {
							range 0..128 {
								error-message "le must be between 0 and 128";
							}
						}
						configd:help "Prefix length to match a netmask less than or equal to it";
					}
				}
			}
			list prefix-list {
				configd:priority "470";
				configd:help "IP prefix-list filter";
				key "tagnode";
				leaf tagnode {
					type string {
						pattern "[-a-zA-Z0-9.]+" {
							error-message "prefix-list name must be alpha-numeric";
						}
					}
					configd:help "IP prefix-list filter";
				}
				leaf description {
					type string;
					configd:help "Description for this prefix-list";
				}
				list rule {
					configd:help "Rule for this prefix-list";
					configd:delete "/opt/vyatta/share/tmplscripts/policy/route/prefix-list/rule/configd_delete.sh";
					configd:end "/opt/vyatta/share/tmplscripts/policy/route/prefix-list/rule/configd_end.sh";
					configd:validate "/opt/vyatta/share/tmplscripts/policy/route/prefix-list/rule/configd_validate1.cli";
					configd:validate "/opt/vyatta/share/tmplscripts/policy/route/prefix-list/rule/configd_validate2.cli";
					key "tagnode";
					leaf tagnode {
						type uint32 {
							range 1..65535 {
								error-message "rule number must be between 1 and 65535";
							}
						}
						configd:help "Rule for this prefix-list";
					}
					leaf description {
						type string;
						configd:help "Description for this rule";
					}
					leaf action {
						type enumeration {
							enum "permit" {
								configd:help "Permit matching prefixes";
							}
							enum "deny" {
								configd:help "Deny matching prefixes";
							}
						}
						configd:help "Action to take on prefixes matching this rule [REQUIRED]";
					}
					leaf ge {
						type uint32 {
							range 0..32 {
								error-message "ge must be between 0 and 32";
							}
						}
						configd:help "Prefix length to match a netmask greater than or equal to it";
					}
					leaf prefix {
						type types:ipv4-prefix;
						configd:help "Prefix to match";
					}
					leaf le {
						type uint32 {
							range 0..32 {
								error-message "le must be between 0 and 32";
							}
						}
						configd:help "Prefix length to match a netmask less than or equal to it";
					}
				}
			}
		}
	}
}
