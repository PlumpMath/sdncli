module vyatta-ipv6-rtradv {
	namespace "urn:vyatta.com:mgmt:vyatta-ipv6-rtradv";
	prefix ipv6-rtradv;

	import vyatta-types {
		prefix types;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}

	organization "Brocade Communications Systems, Inc.";
	contact
		"Brocade Communications Systems, Inc.
		 Postal: 130 Holger Way
		         San Jose, CA 95134
		 E-mail: support@Brocade.com
		 Web: www.brocade.com";

	revision 2014-12-01 {
		description "Update for default-lifetime help text";
	}

	revision 2014-08-27 {
		description "Initial revision.";
		configd:migration 1;
	}

	augment /if:interfaces/interfaces-bridge:bridge/interfaces-bridge:ipv6 {
		leaf dup-addr-detect-transmits {
			type uint32 {
				range 0..max {
					error-message "Value must be >= 0";
				}
			}
			configd:help "Number of NS messages to send while performing DAD";
			default "1";
			configd:update "/opt/vyatta/share/tmplscripts/interfaces/bridge/ipv6/dup-addr-detect-transmits/configd_update.sh";
		}
		container router-advert {
			presence "true";
			configd:priority "999";
			configd:help "Configure parameters for sending Router Advertisements (RAs)";
			configd:end "/opt/vyatta/share/tmplscripts/interfaces/bridge/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/bridge/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/bridge/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/bridge/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/bridge/ipv6/address/eui64/configd_create.sh";
				configd:delete "/opt/vyatta/share/tmplscripts/interfaces/bridge/ipv6/address/eui64/configd_delete.sh";
			}
			leaf autoconf {
				type empty;
				configd:help "Enable acquisition of IPv6 address using stateless autoconfig";
				configd:update "/opt/vyatta/share/tmplscripts/interfaces/bridge/ipv6/address/autoconf/configd_update.sh";
				configd:delete "/opt/vyatta/share/tmplscripts/interfaces/bridge/ipv6/address/autoconf/configd_delete.sh";
			}
		}
		leaf disable-forwarding {
			type empty;
			configd:help "Disable IPv6 forwarding on this interface only";
			configd:create "/opt/vyatta/share/tmplscripts/interfaces/bridge/ipv6/disable-forwarding/configd_create.sh";
			configd:delete "/opt/vyatta/share/tmplscripts/interfaces/bridge/ipv6/disable-forwarding/configd_delete.sh";
		}
	}
	augment /if:interfaces/interfaces-dataplane:dataplane/interfaces-dataplane:ipv6 {
		leaf dup-addr-detect-transmits {
			type uint32 {
				range 0..max {
					error-message "Value must be >= 0";
				}
			}
			configd:help "Number of NS messages to send while performing DAD";
			default "1";
			configd:update "/opt/vyatta/share/tmplscripts/interfaces/dataplane/ipv6/dup-addr-detect-transmits/configd_update.sh";
		}
		container router-advert {
			presence "true";
			configd:priority "999";
			configd:help "Configure parameters for sending Router Advertisements (RAs)";
			configd:end "/opt/vyatta/share/tmplscripts/interfaces/dataplane/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/dataplane/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/dataplane/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/dataplane/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/dataplane/ipv6/address/eui64/configd_create.sh";
				configd:delete "/opt/vyatta/share/tmplscripts/interfaces/dataplane/ipv6/address/eui64/configd_delete.sh";
			}
			leaf autoconf {
				type empty;
				configd:help "Enable acquisition of IPv6 address using stateless autoconfig";
				configd:update "/opt/vyatta/share/tmplscripts/interfaces/dataplane/ipv6/address/autoconf/configd_update.sh";
				configd:delete "/opt/vyatta/share/tmplscripts/interfaces/dataplane/ipv6/address/autoconf/configd_delete.sh";
			}
		}
		leaf disable-forwarding {
			type empty;
			configd:help "Disable IPv6 forwarding on this interface only";
			configd:create "/opt/vyatta/share/tmplscripts/interfaces/dataplane/ipv6/disable-forwarding/configd_create.sh";
			configd:delete "/opt/vyatta/share/tmplscripts/interfaces/dataplane/ipv6/disable-forwarding/configd_delete.sh";
		}
	}
	augment /if:interfaces/interfaces-dataplane:dataplane/interfaces-dataplane:vif/interfaces-dataplane:ipv6 {
		leaf dup-addr-detect-transmits {
			type uint32 {
				range 0..max {
					error-message "Value must be >= 0";
				}
			}
			configd:help "Number of NS messages to send while performing DAD";
			default "1";
			configd:update "/opt/vyatta/share/tmplscripts/interfaces/dataplane/vif/ipv6/dup-addr-detect-transmits/configd_update.sh";
		}
		container router-advert {
			presence "true";
			configd:priority "999";
			configd:help "Configure parameters for sending Router Advertisements (RAs)";
			configd:end "/opt/vyatta/share/tmplscripts/interfaces/dataplane/vif/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/dataplane/vif/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/dataplane/vif/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/dataplane/vif/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/dataplane/vif/ipv6/address/eui64/configd_create.sh";
				configd:delete "/opt/vyatta/share/tmplscripts/interfaces/dataplane/vif/ipv6/address/eui64/configd_delete.sh";
			}
			leaf autoconf {
				type empty;
				configd:help "Enable acquisition of IPv6 address using stateless autoconfig";
				configd:update "/opt/vyatta/share/tmplscripts/interfaces/dataplane/vif/ipv6/address/autoconf/configd_update.sh";
				configd:delete "/opt/vyatta/share/tmplscripts/interfaces/dataplane/vif/ipv6/address/autoconf/configd_delete.sh";
			}
		}
		leaf disable-forwarding {
			type empty;
			configd:help "Disable IPv6 forwarding on this interface only";
			configd:create "/opt/vyatta/share/tmplscripts/interfaces/dataplane/vif/ipv6/disable-forwarding/configd_create.sh";
			configd:delete "/opt/vyatta/share/tmplscripts/interfaces/dataplane/vif/ipv6/disable-forwarding/configd_delete.sh";
		}
	}
	augment /if:interfaces/interfaces-l2tpeth:l2tpeth/interfaces-l2tpeth:ipv6 {
		leaf dup-addr-detect-transmits {
			type uint32 {
				range 0..max {
					error-message "Value must be >= 0";
				}
			}
			configd:help "Number of NS messages to send while performing DAD";
			default "1";
			configd:update "/opt/vyatta/share/tmplscripts/interfaces/l2tpeth/ipv6/dup-addr-detect-transmits/configd_update.sh";
		}
		container router-advert {
			presence "true";
			configd:priority "999";
			configd:help "Configure parameters for sending Router Advertisements (RAs)";
			configd:end "/opt/vyatta/share/tmplscripts/interfaces/l2tpeth/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/l2tpeth/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/l2tpeth/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/l2tpeth/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/l2tpeth/ipv6/address/eui64/configd_create.sh";
				configd:delete "/opt/vyatta/share/tmplscripts/interfaces/l2tpeth/ipv6/address/eui64/configd_delete.sh";
			}
			leaf autoconf {
				type empty;
				configd:help "Enable acquisition of IPv6 address using stateless autoconfig";
				configd:update "/opt/vyatta/share/tmplscripts/interfaces/l2tpeth/ipv6/address/autoconf/configd_update.sh";
				configd:delete "/opt/vyatta/share/tmplscripts/interfaces/l2tpeth/ipv6/address/autoconf/configd_delete.sh";
			}
		}
		leaf disable-forwarding {
			type empty;
			configd:help "Disable IPv6 forwarding on this interface only";
			configd:create "/opt/vyatta/share/tmplscripts/interfaces/l2tpeth/ipv6/disable-forwarding/configd_create.sh";
			configd:delete "/opt/vyatta/share/tmplscripts/interfaces/l2tpeth/ipv6/disable-forwarding/configd_delete.sh";
		}
	}
	augment /if:interfaces/interfaces-l2tpeth:l2tpeth/interfaces-l2tpeth:vif/interfaces-l2tpeth:ipv6 {
		leaf dup-addr-detect-transmits {
			type uint32 {
				range 0..max {
					error-message "Value must be >= 0";
				}
			}
			configd:help "Number of NS messages to send while performing DAD";
			default "1";
			configd:update "/opt/vyatta/share/tmplscripts/interfaces/l2tpeth/vif/ipv6/dup-addr-detect-transmits/configd_update.sh";
		}
		container router-advert {
			presence "true";
			configd:priority "999";
			configd:help "Configure parameters for sending Router Advertisements (RAs)";
			configd:end "/opt/vyatta/share/tmplscripts/interfaces/l2tpeth/vif/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/l2tpeth/vif/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/l2tpeth/vif/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/l2tpeth/vif/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/l2tpeth/vif/ipv6/address/eui64/configd_create.sh";
				configd:delete "/opt/vyatta/share/tmplscripts/interfaces/l2tpeth/vif/ipv6/address/eui64/configd_delete.sh";
			}
			leaf autoconf {
				type empty;
				configd:help "Enable acquisition of IPv6 address using stateless autoconfig";
				configd:update "/opt/vyatta/share/tmplscripts/interfaces/l2tpeth/vif/ipv6/address/autoconf/configd_update.sh";
				configd:delete "/opt/vyatta/share/tmplscripts/interfaces/l2tpeth/vif/ipv6/address/autoconf/configd_delete.sh";
			}
		}
		leaf disable-forwarding {
			type empty;
			configd:help "Disable IPv6 forwarding on this interface only";
			configd:create "/opt/vyatta/share/tmplscripts/interfaces/l2tpeth/vif/ipv6/disable-forwarding/configd_create.sh";
			configd:delete "/opt/vyatta/share/tmplscripts/interfaces/l2tpeth/vif/ipv6/disable-forwarding/configd_delete.sh";
		}
	}
	augment /if:interfaces/interfaces-loopback:loopback/interfaces-loopback:ipv6 {
		leaf dup-addr-detect-transmits {
			type uint32 {
				range 0..max {
					error-message "Value must be >= 0";
				}
			}
			configd:help "Number of NS messages to send while performing DAD";
			default "1";
			configd:update "/opt/vyatta/share/tmplscripts/interfaces/loopback/ipv6/dup-addr-detect-transmits/configd_update.sh";
		}
		container router-advert {
			presence "true";
			configd:priority "999";
			configd:help "Configure parameters for sending Router Advertisements (RAs)";
			configd:end "/opt/vyatta/share/tmplscripts/interfaces/loopback/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/loopback/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/loopback/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/loopback/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/loopback/ipv6/address/eui64/configd_create.sh";
				configd:delete "/opt/vyatta/share/tmplscripts/interfaces/loopback/ipv6/address/eui64/configd_delete.sh";
			}
			leaf autoconf {
				type empty;
				configd:help "Enable acquisition of IPv6 address using stateless autoconfig";
				configd:update "/opt/vyatta/share/tmplscripts/interfaces/loopback/ipv6/address/autoconf/configd_update.sh";
				configd:delete "/opt/vyatta/share/tmplscripts/interfaces/loopback/ipv6/address/autoconf/configd_delete.sh";
			}
		}
		leaf disable-forwarding {
			type empty;
			configd:help "Disable IPv6 forwarding on this interface only";
			configd:create "/opt/vyatta/share/tmplscripts/interfaces/loopback/ipv6/disable-forwarding/configd_create.sh";
			configd:delete "/opt/vyatta/share/tmplscripts/interfaces/loopback/ipv6/disable-forwarding/configd_delete.sh";
		}
	}
	augment /if:interfaces/interfaces-openvpn:openvpn/interfaces-openvpn:ipv6 {
		leaf dup-addr-detect-transmits {
			type uint32 {
				range 0..max {
					error-message "Value must be >= 0";
				}
			}
			configd:help "Number of NS messages to send while performing DAD";
			default "1";
			configd:update "/opt/vyatta/share/tmplscripts/interfaces/openvpn/ipv6/dup-addr-detect-transmits/configd_update.sh";
		}
		container router-advert {
			presence "true";
			configd:priority "999";
			configd:help "Configure parameters for sending Router Advertisements (RAs)";
			configd:end "/opt/vyatta/share/tmplscripts/interfaces/openvpn/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/openvpn/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/openvpn/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/openvpn/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/openvpn/ipv6/address/eui64/configd_create.sh";
				configd:delete "/opt/vyatta/share/tmplscripts/interfaces/openvpn/ipv6/address/eui64/configd_delete.sh";
			}
			leaf autoconf {
				type empty;
				configd:help "Enable acquisition of IPv6 address using stateless autoconfig";
				configd:update "/opt/vyatta/share/tmplscripts/interfaces/openvpn/ipv6/address/autoconf/configd_update.sh";
				configd:delete "/opt/vyatta/share/tmplscripts/interfaces/openvpn/ipv6/address/autoconf/configd_delete.sh";
			}
		}
		leaf disable-forwarding {
			type empty;
			configd:help "Disable IPv6 forwarding on this interface only";
			configd:create "/opt/vyatta/share/tmplscripts/interfaces/openvpn/ipv6/disable-forwarding/configd_create.sh";
			configd:delete "/opt/vyatta/share/tmplscripts/interfaces/openvpn/ipv6/disable-forwarding/configd_delete.sh";
		}
	}
	augment /if:interfaces/interfaces-tunnel:tunnel/interfaces-tunnel:ipv6 {
		leaf dup-addr-detect-transmits {
			type uint32 {
				range 0..max {
					error-message "Value must be >= 0";
				}
			}
			configd:help "Number of NS messages to send while performing DAD";
			default "1";
			configd:update "/opt/vyatta/share/tmplscripts/interfaces/tunnel/ipv6/dup-addr-detect-transmits/configd_update.sh";
		}
		container router-advert {
			presence "true";
			configd:priority "999";
			configd:help "Configure parameters for sending Router Advertisements (RAs)";
			configd:end "/opt/vyatta/share/tmplscripts/interfaces/tunnel/ipv6/router-advert/configd_end.sh";
			leaf retrans-timer {
				type uint32;
				configd:help "Value to place in \"Retrans Timer\" field in RAs.";
				default "0";
			}
			leaf link-mtu {
				type uint32 {
					configd:syntax "/opt/vyatta/share/tmplscripts/interfaces/tunnel/ipv6/router-advert/link-mtu/configd_syntax1.cli";
				}
				configd:help "Value of link MTU to place in RAs";
				default "0";
			}
			leaf min-interval {
				type uint32 {
					range 3..1350 {
						error-message "Value must be between 3 and 1350";
					}
				}
				configd:help "Minimum interval between unsolicited multicast RAs";
			}
			leaf default-preference {
				type enumeration {
					enum "low" {
						configd:help "Default router is low preference";
					}
					enum "medium" {
						configd:help "Default router is medium preference (Default)";
					}
					enum "high" {
						configd:help "Default router is high preference";
					}
				}
				configd:help "Default router preference";
			}
			list prefix {
				configd:help "IPv6 prefix to be advertised in Router Advertisements (RAs)";
				key "tagnode";
				leaf tagnode {
					type types:ipv6-prefix;
					configd:help "IPv6 prefix to be advertised in Router Advertisements (RAs)";
				}
				leaf on-link-flag {
					type boolean;
					configd:help "Flag that prefix can be used for on-link determination";
					default "true";
				}
				leaf preferred-lifetime {
					type string {
						configd:syntax "/opt/vyatta/share/tmplscripts/interfaces/tunnel/ipv6/router-advert/prefix/preferred-lifetime/configd_syntax1.cli";
					}
					configd:help "Time in seconds that the prefix will remain preferred";
				}
				leaf autonomous-flag {
					type boolean;
					configd:help "Whether prefix can be used for address auto-configuration";
					default "true";
				}
				leaf valid-lifetime {
					type string {
						configd:syntax "/opt/vyatta/share/tmplscripts/interfaces/tunnel/ipv6/router-advert/prefix/valid-lifetime/configd_syntax1.cli";
					}
					configd:help "Time in seconds that the prefix will remain valid";
					default "2592000";
				}
			}
			leaf cur-hop-limit {
				type uint32 {
					range 0..255 {
						error-message "Value must be between 0 and 255";
					}
				}
				configd:help "Value to be placed in the \"Current Hop Limit\" field in RAs";
				default "64";
			}
			leaf max-interval {
				type uint32 {
					range 4..1800 {
						error-message "Value must be between 4 and 1800";
					}
				}
				configd:help "Maximum interval between unsolicited multicast RAs";
				default "600";
			}
			leaf managed-flag {
				type boolean;
				configd:help "Value for \"managed address configuration\" flag in RAs";
				default "false";
			}
			leaf send-advert {
				type boolean;
				configd:help "Enable/disable sending RAs";
				default "true";
			}
			leaf default-lifetime {
				type uint32 {
					range "0|4..9000"; 
				}
				configd:help "Value to be placed in \"Router Lifetime\" field in RAs";
			}
			leaf reachable-time {
				type uint32 {
					range 0..3600000 {
						error-message "Value must be between 0 and 3,600,000 milliseconds (1 hour)";
					}
				}
				configd:help "Value to be placed in \"Reachable Time\" field in RAs";
				default "0";
			}
			leaf other-config-flag {
				type boolean;
				configd:help "Value to be placed in the \"other configuration\" flag in RAs";
				default "false";
			}
		}
		container address {
			presence "true";
			configd:help "IPv6 address auto-configuration modes";
			leaf-list eui64 {
				type types:ipv6-prefix {
					pattern ".*/64" {
						error-message "prefix length must be 64";
					}
				}
				ordered-by "user";
				configd:help "Assign IPv6 address using EUI-64 based on MAC address";
				configd:create "/opt/vyatta/share/tmplscripts/interfaces/tunnel/ipv6/address/eui64/configd_create.sh";
				configd:delete "/opt/vyatta/share/tmplscripts/interfaces/tunnel/ipv6/address/eui64/configd_delete.sh";
			}
			leaf autoconf {
				type empty;
				configd:help "Enable acquisition of IPv6 address using stateless autoconfig";
				configd:update "/opt/vyatta/share/tmplscripts/interfaces/tunnel/ipv6/address/autoconf/configd_update.sh";
				configd:delete "/opt/vyatta/share/tmplscripts/interfaces/tunnel/ipv6/address/autoconf/configd_delete.sh";
			}
		}
		leaf disable-forwarding {
			type empty;
			configd:help "Disable IPv6 forwarding on this interface only";
			configd:create "/opt/vyatta/share/tmplscripts/interfaces/tunnel/ipv6/disable-forwarding/configd_create.sh";
			configd:delete "/opt/vyatta/share/tmplscripts/interfaces/tunnel/ipv6/disable-forwarding/configd_delete.sh";
		}
	}
}
