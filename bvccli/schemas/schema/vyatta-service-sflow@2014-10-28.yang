module vyatta-service-sflow {
	namespace "urn:vyatta.com:mgmt:vyatta-service-sflow";
	prefix service-sflow;

	import vyatta-types {
		prefix types;
	}
	import vyatta-services {
		prefix service;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /service:service {
		container sflow {
			presence "true";
			configd:help "sflow configuration for dataplane";
			leaf polling-interval {
				type uint32 {
					range 0..65535 {
						error-message "Sampling rate must be between o and 65535";
					}
				}
				default "20";
				configd:help "sFlow polling interval";
				configd:update "vyatta-sflow.pl --cmd=enable --proto=polling-interval --state=$VAR(@) --param=0";
			}
			leaf sampling-rate {
				type uint32 {
					range 512..65535 {
						error-message "Sampling rate must be between 512 and 65535";
					}
				}
				default "2048";
				configd:help "sFlow sampling rate";
				configd:update "vyatta-sflow.pl --cmd=enable --proto=sampling-rate --state=$VAR(@) --param=0";
			}
			leaf agent-address {
				type union {
					type types:ipv4-address;
					type types:ipv6-address;
				}
				configd:priority "400";
				configd:help "Agent address";
				configd:delete "vyatta-sflow.pl --cmd=disable --proto=agent-address --state=$VAR(@) --param=0";
				configd:update "vyatta-sflow.pl --cmd=enable --proto=agent-address --state=$VAR(@) --param=0";
			}
			list server-port {
				configd:help "sFlow server UDP port";
				key "tagnode";
				leaf tagnode {
					type uint32 {
						range 1..65535 {
							error-message "Server port must be between 1 and 65535";
						}
					}
					configd:help "sFlow server UDP port";
				}
				leaf-list server-address {
					type union {
						type types:ipv4-address;
						type types:ipv6-address;
					}
					ordered-by "user";
					configd:help "Server address";
					configd:delete "vyatta-sflow.pl --cmd=disable --proto=server --state=$VAR(@) --param=$VAR(../@)";
					configd:update "vyatta-sflow.pl --cmd=enable --proto=server --state=$VAR(@) --param=$VAR(../@)";
				}
			}
		}
	}
}
