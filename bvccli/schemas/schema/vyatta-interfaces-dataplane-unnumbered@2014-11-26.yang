module vyatta-interfaces-dataplane-unnumbered {
	namespace "urn:vyatta.com:mgmt:vyatta-interfaces-unnumbered";
	prefix interfaces-dataplane-unnumbered;

	import vyatta-protocols {
		prefix protocols;
	}
	import vyatta-types {
		prefix types;
	}
	import configd {
		prefix configd;
	}
	import vyatta-interfaces {
		prefix if;
	}
	import vyatta-interfaces-dataplane {
		prefix interfaces-dataplane;
	}

	organization "Brocade Communications Systems, Inc.";
	contact
		"Brocade Communications Systems, Inc.
		 Postal: 130 Holger Way
		         San Jose, CA 95134
		 E-mail: support@Brocade.com
		 Web: www.brocade.com";


	revision 2014-11-26 {
		description "Update for interface types";
	}

	revision 2014-10-28 {
		description "Update for 3.2.1R1";
	}
	
	revision 2014-10-06 {
		description "Initial revision.";
	}

	grouping unnumbered-opts {
			list donor-interface {
				max-elements  "1";
				configd:help "donor interface name";
				configd:allowed "/opt/vyatta/share/tmplscripts/interfaces/dataplane/unnumbered/unnumbered-allowed.sh";
				key "tagnode";
				leaf tagnode {
					type union {
						type string {
							pattern "lo(|[1-9]([0-9]){0,4})";
							configd:pattern-help "<lo|loN>";
						}
						type interfaces-dataplane:dataplane-ifname;
					}
				}
				leaf preferred-address {
					type types:ipv4-address;
					configd:help "preferred address to use from donor interface";
					configd:allowed "/opt/vyatta/share/tmplscripts/interfaces/dataplane/unnumbered/preferred-address/configd_allowed.sh";
				}
				configd:validate "/opt/vyatta/share/tmplscripts/interfaces/dataplane/unnumbered/unnumbered-validate.sh";
			}
	}

	augment /if:interfaces/interfaces-dataplane:dataplane/interfaces-dataplane:ip {
		container unnumbered {
			configd:help "Enable unnumbered IP";
			configd:priority "330";
			configd:end "/opt/vyatta/sbin/vyatta-update-unnumbered.pl --dev=$VAR(../../@)";
			uses unnumbered-opts;
		}
	}
	augment /if:interfaces/interfaces-dataplane:dataplane/interfaces-dataplane:vif/interfaces-dataplane:ip {
		container unnumbered {
			configd:help "Enable unnumbered IP";
			configd:priority "330";
			configd:end "/opt/vyatta/sbin/vyatta-update-unnumbered.pl --dev=$VAR(../../../@).$VAR(../../@)";
			uses unnumbered-opts;
		}
	}
}
