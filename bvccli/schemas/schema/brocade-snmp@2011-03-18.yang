/***********************************************************************
 * brocade-snmp.yang: Brocade SNMP server Data Model
 *
 * April 2011,Ganesan Varadharajan
 *
 * Copyright (c) 2011 by Brocade Communications Systems, Inc.
 * All rights reserved.
 *
 **********************************************************************/
module brocade-snmp {
    namespace "urn:brocade.com:mgmt:brocade-snmp";
    prefix "snmp-server";

  	import tailf-common {
    	prefix tailf;
  	}

    import brocade-rbridge {
        prefix rbridge;
    }

    import ietf-inet-types {
        prefix inet;
    }

    organization
        "Brocade Communications Systems, Inc.";

    contact
        "Address :  120 Holger Way
                    San Jose, CA 95134
                    U.S.A
        Phone    :  +1-408-333-8000
        E-mail   :  support@brocade.com
        Website  :  www.brocade.com";

    description
        "Data Model for SNMP Server and related configuration CLIs";

    revision "2011-03-18" {
        description
            "Formatting yang model according to guidelines";
    }

	
	typedef host-port {
		type uint32 {
            range "0 .. 65535" {
                error-message "Port number should be in the range 0-65535";
		    }
        }
		default 162;
    }

	typedef host-version {
		type enumeration {
            enum 1 {
                value 0;
            }
            enum 2c {
                value 1;
            }
			}
		}
    typedef snmp-engineID {
        type string {
        pattern '[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]';
        }
    }
    

	typedef system-contact {
        type string {
            length "4 .. 256" {
            error-message "Invalid Contact String length. String size 
                           must be between 4 and 255";
            }
        }
		}

	typedef system-location {
        type string {
            length "4 .. 256" {
            error-message "Invalid Location String length. String size
                           must be between 4 and 255";
            }
        }
    }

    typedef system-description {
        type string {
            length "4 .. 256" {
            error-message "Invalid System Description String length.
                           String size must be between 4 and 255";
            }
        }
    }

    typedef sev-level {
        type enumeration {
            enum None;
            enum Critical;
            enum Error;
            enum Warning;
            enum Info;
            enum Debug;
        }
		default None;
    }
			
	typedef mib-access {
		type enumeration {
			enum included {
				value 1;
			}
			enum excluded {
				value 2;
			}
		}
	}

	typedef group-version-type {
		type enumeration {
			enum v1 {
				value 0;
			}
			enum v2c {
				value 1;
			}
			enum v3 {
				value 2;
			}
		}
	}

	typedef auth-mode-option{
		type enumeration {
			enum noauth {
				value 1;
			}
			enum auth {
				value 2;
			}
			enum priv {
				value 3;
			}
		}
	}

    container snmp-server {

        list context {
            description 
                "provides the  mapping of SNMP context (represented by
                 the value of vacmContextName) to the various entities
                 within the entities within the managed device";

            key "context-name";
			max-elements 256;
            leaf context-name {
         		type string {
				}
            }
            leaf vrf-name {
              type string {
            }
            }
        }
        /*
         * Note: 256 community entries can be allowed to configure including 6 default communities(3ro + 3rw).
         *    where all 256 are user configurable(ro/rw) communities.
         */
        list community {
    	    key "community";
			max-elements 256;
            leaf community {
                type string {
				}
            }
			
			leaf groupname {
				type string {
                }
				default "";
			}
			
		}

        list user {
            key "username";
            max-elements 10;
        	uses snmpv3user-group;
        }

        list v3host {
            key "hostip username";
            max-elements 6;
        	uses snmpv3host-group;
        }

         /*
         * Note: Only 12 host trap targets can be configured.
         *         6 each version.
         */
        list host {
            key "ip community";
            max-elements 12;
            leaf ip {
				type inet:host;
            }

            leaf version {
                type host-version;
                default 1;
            }
            leaf community {
		type string;
            }
            leaf udp-port {
                type host-port;
            }
            leaf severity-level {
                type sev-level;
            }
        }

	   	container agtconfig {
			leaf contact {
            	type system-contact; 
        	}
			leaf location {
            	type system-location;
        	}
            leaf sys-descr {
                type system-description;
			}
		}
		container enable {
			container trap { 
				leaf trap-flag {
                    type empty;
				}
			}
		}

        container engineID-drop {
			uses engineID-group;
            }

		list view {
			max-elements 10;
			key "viewname mibtree";
			leaf viewname {
				type string {
					length "1 .. 32" {
					}
				}
			}
			leaf mibtree {
				type string {
					length "1 .. 256" {
					}
				}
			}
			leaf mibtree-access {
				type mib-access;
			}
		}

		list group {
//            tailf:cli-incomplete-command;
			max-elements 10;
			key "group-name group-version";
			leaf group-name {
				type string {
					length "1 .. 32" {
					}
				}
			}
			leaf group-version {
				type group-version-type;
			}
			leaf group-auth-mode {
				type auth-mode-option;
				default noauth;
			}
			leaf read {
				type string {
					length "1 .. 32" {
					}
				}
				default "-";
			}
			leaf write {
				type string {
					length "1 .. 32" {
					}
				}
				default "-";
			}
			leaf notify {
				type string {
					length "1 .. 32" {
					}
				}
				default "-";
			}
		}
	}

grouping engineID-group {
        container engineID {
            leaf local {
                type snmp-engineID;
                }
            }
	}
grouping snmpv3user-group {


            leaf username {
                type string {
                    length "1 .. 25" {
                        error-message "Username length should be in the range 1-25";
                    }
                }
            }
            leaf groupname {
                type string {
				}
                default "";
            }
            leaf auth {
                type enumeration {
                    enum md5 {
                        value 0;
                    }
                    enum sha {
                        value 1;
                    }
                    enum noauth {
                        value 2;
                    }
                }
                default noauth;
            }
            leaf auth-password {
                type string {
				}
                default "";
            }
            leaf priv {
                type enumeration {
                    enum DES {
                        value 0;
                    }
                    enum nopriv {
                        value 1;
                    }
                    enum AES128 {
                        value 2;
                    }
                }
                default nopriv;
            }
            leaf priv-password {
                type string {
				}
                default "";
            }
			leaf encrypted {
				type empty;
				mandatory false;
			}
	}

grouping snmpv3host-group {

            leaf hostip {
				type inet:host;
				}
            leaf username {
		 		type string;
            }
            leaf udp-port {
                type host-port;
            }
            leaf notifytype {
                type enumeration {
                    enum traps {
                        value 0;
                    }
                    enum informs {
                        value 1;
                    }
                }
                default traps;
            }
            leaf engineid {
                type string {
				}
                default "00:00:00:00:00:00:00:00:00";
            }
			leaf severity-level {
                type sev-level;
            }
	}

    augment "/rbridge:rbridge-id" {
		container snmp-server {
        	uses engineID-group;
        	list user {
            	key "username";
            	max-elements 10;
        		uses snmpv3user-group;
			}

        	list v3host {
            key "hostip username";
            max-elements 6;
        	uses snmpv3host-group;
			}
		}
	}
}
