module vyatta-system-login {
	namespace "urn:vyatta.com:mgmt:vyatta-system-login";
	prefix system-login;

	import vyatta-types {
		prefix types;
	}
	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-01-28 {
		description "Disallow empty user passwords.";
	}
	revision 2014-08-27 {
		description "Initial revision.";
		configd:migration 1;
	}

	augment /system:system {
		container login {
			presence "true";
			configd:priority "400";
			configd:help "User login";
			configd:delete "/opt/vyatta/share/tmplscripts/system/login/configd_delete.sh";
			configd:end "/opt/vyatta/share/tmplscripts/system/login/configd_end.sh";
			leaf session-timeout {
				type uint32 {
					range 0..1000000 {
						error-message "Timeout must be between 0 and 1000000";
					}
				}
				configd:help "Idle Session timeout";
				default "0";
				configd:update "/opt/vyatta/share/tmplscripts/system/login/session-timeout/configd_update.sh";
			}
			list radius-server {
				configd:help "Radius server authentication";
				configd:validate "/opt/vyatta/share/tmplscripts/system/login/radius-server/configd_validate1.cli";
				key "tagnode";
				leaf tagnode {
					type types:ipv4-address;
					configd:help "Radius server authentication";
				}
				leaf port {
					type uint32 {
						range 1..65535 {
							error-message "Port number must be in range 1 to 65535";
						}
					}
					configd:help "Radius port [REQUIRED]";
					default "1812";
				}
				leaf secret {
					type string;
					configd:help "Secret for radius access [REQUIRED]";
				}
				leaf timeout {
					type uint32 {
						range 1..30 {
							error-message "Timeout must be between 1 and 30 seconds";
						}
					}
					configd:help "Timeout for radius session [REQUIRED]";
					default "2";
				}
			}
			list group {
				configd:help "Group name";
				configd:update "/opt/vyatta/share/tmplscripts/system/login/group/configd_update.sh";
				configd:delete "/opt/vyatta/share/tmplscripts/system/login/group/configd_delete.sh";
				key "tagnode";
				leaf tagnode {
					type string;
					configd:help "Group name";
				}
				leaf description {
					type string;
					configd:help "Description";
				}
			}
			list user {
				configd:help "User account information";
				configd:validate "/opt/vyatta/share/tmplscripts/system/login/user/configd_validate1.cli";
				key "tagnode";
				leaf tagnode {
					type string {
						pattern "[a-zA-Z_][a-zA-Z0-9_-]*" {
							configd:error-message "Username should only contain lower case letters, digits, underscores or dashes"; 
						}
						configd:syntax "/opt/vyatta/share/tmplscripts/system/login/user/configd_syntax1.cli";
					}
					configd:help "User account information";
				}
				container authentication {
					presence "true";
					configd:help "Authentication password";
					leaf plaintext-password {
						type string {
							configd:syntax "/opt/vyatta/share/tmplscripts/system/login/user/authentication/plaintext-password/configd_syntax.cli";
						}
						configd:secret "true";
						configd:help "Plaintext password for encryption";
						configd:subst "/opt/vyatta/share/tmplscripts/system/login/user/authentication/plaintext-password/configd_subst1.cli";
					}
					list public-keys {
						configd:help "Remote access public keys";
						configd:validate "/opt/vyatta/share/tmplscripts/system/login/user/authentication/public-keys/configd_validate1.cli";
						configd:validate "/opt/vyatta/share/tmplscripts/system/login/user/authentication/public-keys/configd_validate2.cli";
						key "tagnode";
						leaf tagnode {
							type string;
							configd:help "Remote access public keys";
						}
						leaf options {
							type string;
							configd:help "Additional public key options";
						}
						leaf key {
							type string {
								pattern "[0-9A-Za-z\+/=]*" {
									error-message "Invalid public key character not base-64";
								}
							}
							configd:help "Public key value (base64-encoded)";
							configd:comp_help "/opt/vyatta/share/tmplscripts/system/login/user/authentication/public-keys/key/configd_comp_help.txt";
						}
						leaf type {
							type string {
								configd:syntax "/opt/vyatta/share/tmplscripts/system/login/user/authentication/public-keys/type/configd_syntax1.cli";
							}
							configd:help "Public key type";
							configd:allowed "/opt/vyatta/share/tmplscripts/system/login/user/authentication/public-keys/type/configd_allowed.sh";
						}
					}
					leaf encrypted-password {
						type string {
							configd:syntax "/opt/vyatta/share/tmplscripts/system/login/user/authentication/encrypted-password/configd_syntax1.cli";
						}
						configd:secret "true";
						configd:help "Encrypted password";
					}
				}
				leaf home-directory {
					type string;
					configd:help "Home directory";
				}
				leaf-list group {
					type string {
						pattern "[a-zA-Z_][a-zA-Z0-9_-]*$?" {
							configd:error-message "Invalid group name $VAR(@)";
						}
						configd:syntax "/opt/vyatta/share/tmplscripts/system/login/user/group/configd_syntax1.cli";
					}
					ordered-by "user";
					configd:help "Additional group membership";
					configd:allowed "/opt/vyatta/share/tmplscripts/system/login/user/group/configd_allowed.sh";
					configd:validate "/opt/vyatta/share/tmplscripts/system/login/user/group/configd_validate1.cli";
				}
				leaf level {
					type enumeration {
						enum "admin" {
							configd:help "Administrators";
						}
						enum "operator" {
							configd:help "Operators";
						}
						enum "superuser" {
							configd:help "Superusers";
						}
					}
					configd:help "User privilege level";
					default "admin";
					configd:allowed "/opt/vyatta/share/tmplscripts/system/login/user/level/configd_allowed.sh";
				}
				leaf full-name {
					type string {
						pattern "[^:]*" {
							error-message "Cannot use ':' in full name";
						}
					}
					configd:help "Full name of the user (use quotes for names with spaces)";
				}
			}
			container banner {
				presence "true";
				configd:help "System login banners";
				leaf pre-login {
					type string;
					configd:help "System loging banner pre-login";
					configd:update "/opt/vyatta/share/tmplscripts/system/login/banner/pre-login/configd_update.sh";
					configd:delete "/opt/vyatta/share/tmplscripts/system/login/banner/pre-login/configd_delete.sh";
					configd:comp_help "/opt/vyatta/share/tmplscripts/system/login/banner/pre-login/configd_comp_help.txt";
				}
				leaf post-login {
					type string;
					configd:help "System loging banner post-login";
					configd:update "/opt/vyatta/share/tmplscripts/system/login/banner/post-login/configd_update.sh";
					configd:delete "/opt/vyatta/share/tmplscripts/system/login/banner/post-login/configd_delete.sh";
					configd:comp_help "/opt/vyatta/share/tmplscripts/system/login/banner/post-login/configd_comp_help.txt";
				}
			}
		}
	}
}
