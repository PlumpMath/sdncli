module vyatta-interfaces-dataplane {
	namespace "urn:vyatta.com:mgmt:vyatta-interfaces-dataplane";
	prefix interfaces-dataplane;

	import vyatta-interfaces {
		prefix if;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-01-09 {
		description "Modified dhcpv6-options priority";
	}
	revision 2014-11-26 {
		description "Update interface typedef and datalane end action";
	}
	revision 2014-10-28 {
		description "Update for 3.2.1R1";
	}
	
	revision 2014-08-27 {
		description "Initial revision.";
		configd:migration 1;
	}

	typedef dataplane-ifname {
		type union {
			type string {
				pattern "dp[0-9]+(P[0-9]+)?p[0-9]{1,3}p[0-9]{1,3}";
				configd:pattern-help "<dpFpNpS>";
			}
			type string {
				pattern "dp[0-9]+em[0-9]+";
				configd:pattern-help "<dpFemN>";
			}
			type string {
				pattern "dp[0-9]+(P[0-9]+)?s[0-9]+(f[0-9])?";
				configd:pattern-help "<dpFsN>";
			}
		}
	}

	augment /if:interfaces {
		list dataplane {
			configd:priority "318";
			configd:help "Dataplane interface name";
			configd:allowed "/opt/vyatta/share/tmplscripts/interfaces/dataplane/configd_allowed.sh";
			configd:create "/opt/vyatta/share/tmplscripts/interfaces/dataplane/configd_create.sh";
			configd:delete "/opt/vyatta/share/tmplscripts/interfaces/dataplane/configd_delete.sh";
			configd:validate "/opt/vyatta/share/tmplscripts/interfaces/dataplane/configd_validate1.cli";
			configd:end "/opt/vyatta/sbin/vyatta-unnumbered-update-donor.pl --dev=$VAR(@)";
			key "tagnode";
			leaf tagnode {
				type dataplane-ifname;
				configd:help "Dataplane interface name";
				configd:allowed "/opt/vyatta/share/tmplscripts/interfaces/dataplane/configd_allowed.sh";
			}
			leaf description {
				type string;
				configd:help "Description";
				configd:update "/opt/vyatta/share/tmplscripts/interfaces/dataplane/description/configd_update.sh";
				configd:delete "/opt/vyatta/share/tmplscripts/interfaces/dataplane/description/configd_delete.sh";
			}
			container dhcpv6-options {
				presence "true";
				configd:priority "319";
				configd:help "DHCPv6 options";
				configd:end "/opt/vyatta/share/tmplscripts/interfaces/dataplane/dhcpv6-options/configd_end.sh";
				configd:validate "/opt/vyatta/share/tmplscripts/interfaces/dataplane/dhcpv6-options/configd_validate1.cli";
				leaf parameters-only {
					type empty;
					configd:help "Acquire only config parameters, not address";
				}
				leaf temporary {
					type empty;
					configd:help "IPv6 \"temporary\" address";
				}
			}
			container ip {
				leaf enable-proxy-arp {
					type empty;
					configd:help "Enable proxy-arp on this interface";
					configd:create "/opt/vyatta/share/tmplscripts/interfaces/dataplane/ip/enable-proxy-arp/configd_create.sh";
					configd:delete "/opt/vyatta/share/tmplscripts/interfaces/dataplane/ip/enable-proxy-arp/configd_delete.sh";
				}
				leaf rpf-check {
					type enumeration {
						enum "strict" {
							configd:help "Enable Strict Reverse Path Forwarding as defined in RFC3704";
						}
						enum "loose" {
							configd:help "Enable Loose Reverse Path Forwarding as defined in RFC3704";
						}
						enum "disable" {
							configd:help "No source validation";
						}
					}
					configd:help "Policy for reverse path filter, as specified in RFC3704";
					default "disable";
					configd:update "/opt/vyatta/share/tmplscripts/interfaces/dataplane/ip/rpf-check/configd_update.sh";
					configd:delete "/opt/vyatta/share/tmplscripts/interfaces/dataplane/ip/rpf-check/configd_delete.sh";
				}
				leaf disable-forwarding {
					type empty;
					configd:help "Disable IPv4 forwarding on this interface";
					configd:create "/opt/vyatta/share/tmplscripts/interfaces/dataplane/ip/disable-forwarding/configd_create.sh";
					configd:delete "/opt/vyatta/share/tmplscripts/interfaces/dataplane/ip/disable-forwarding/configd_delete.sh";
				}
			}
			container ipv6 {
				presence "true";
				configd:help "IPv6 parameters";
			}
			leaf log_martians {
			    type empty;
			    configd:help "Enable the logging of bogus packets";
			    configd:create "echo 1 > /proc/sys/net/ipv4/conf/$VAR(../@)/log_martians";
			    configd:delete "echo 0 > /proc/sys/net/ipv4/conf/$VAR(../@)/log_martians";
			}
			leaf mtu {
				type uint32 {
					range 68..9000 {
						error-message "MTU must be between 68 and 9000";
					}
				}
				configd:priority "381";
				configd:help "Maximum Transmission Unit (MTU)";
				default "1500";
				configd:update "/opt/vyatta/share/tmplscripts/interfaces/dataplane/mtu/configd_update.sh";
				configd:delete "/opt/vyatta/share/tmplscripts/interfaces/dataplane/mtu/configd_delete.sh";
			}
			leaf disable {
				type empty;
				configd:help "Disable interface";
				configd:create "/opt/vyatta/share/tmplscripts/interfaces/dataplane/disable/configd_create.sh";
				configd:delete "/opt/vyatta/share/tmplscripts/interfaces/dataplane/disable/configd_delete.sh";
			}
			list vif {
				configd:priority "319";
				configd:help "Virtual Interface (VIF) ID";
				configd:create "/opt/vyatta/share/tmplscripts/interfaces/dataplane/vif/configd_create.sh";
				configd:delete "/opt/vyatta/share/tmplscripts/interfaces/dataplane/vif/configd_delete.sh";
				configd:validate "/opt/vyatta/share/tmplscripts/interfaces/dataplane/vif/configd_validate1.cli";
				key "tagnode";
				leaf tagnode {
					type uint32 {
						range 1..4094 {
							error-message "VIF ID must be between 1 and 4094";
						}
					}
					configd:help "Virtual Interface (VIF) ID";
				}
				leaf vlan {
					type uint32 {
						range 1..4094 {
							error-message "VLAN ID must be between 1 and 4094";
						}
					}
					configd:help "Virtual Local Area Network (VLAN) ID";
				}
				leaf description {
					type string;
					configd:help "Description";
					configd:update "/opt/vyatta/share/tmplscripts/interfaces/dataplane/vif/description/configd_update.sh";
					configd:delete "/opt/vyatta/share/tmplscripts/interfaces/dataplane/vif/description/configd_delete.sh";
				}
				container dhcpv6-options {
					presence "true";
					configd:priority "320";
					configd:help "DHCPv6 options";
					configd:end "/opt/vyatta/share/tmplscripts/interfaces/dataplane/vif/dhcpv6-options/configd_end.sh";
					configd:validate "/opt/vyatta/share/tmplscripts/interfaces/dataplane/vif/dhcpv6-options/configd_validate1.cli";
					leaf parameters-only {
						type empty;
						configd:help "Acquire only config parameters, not address";
					}
					leaf temporary {
						type empty;
						configd:help "IPv6 \"temporary\" address";
					}
				}
				container ip {
					presence "true";
					leaf enable-proxy-arp {
						type empty;
						configd:help "Enable proxy-arp on this interface";
						configd:create "/opt/vyatta/share/tmplscripts/interfaces/dataplane/vif/ip/enable-proxy-arp/configd_create.sh";
						configd:delete "/opt/vyatta/share/tmplscripts/interfaces/dataplane/vif/ip/enable-proxy-arp/configd_delete.sh";
					}
					leaf rpf-check {
						type enumeration {
							enum "strict" {
								configd:help "Enable Strict Reverse Path Forwarding as defined in RFC3704";
							}
							enum "loose" {
								configd:help "Enable Loose Reverse Path Forwarding as defined in RFC3704";
							}
							enum "disable" {
								configd:help "No source validation";
							}
						}
						configd:help "Policy for reverse path filter, as specified in RFC3704";
						default "disable";
						configd:update "/opt/vyatta/share/tmplscripts/interfaces/dataplane/vif/ip/rpf-check/configd_update.sh";
						configd:delete "/opt/vyatta/share/tmplscripts/interfaces/dataplane/vif/ip/rpf-check/configd_delete.sh";
					}
				}
				container ipv6 {
					presence "true";
					configd:help "IPv6 parameters";
				}
				leaf mtu {
					type uint32 {
						range 68..9000 {
							error-message "MTU must be between 68 and 9000";
						}
					}
					configd:priority "381";
					configd:help "Maximum Transmission Unit (MTU)";
					configd:update "/opt/vyatta/share/tmplscripts/interfaces/dataplane/vif/mtu/configd_update.sh";
					configd:delete "/opt/vyatta/share/tmplscripts/interfaces/dataplane/vif/mtu/configd_delete.sh";
				}
				leaf disable {
					type empty;
					configd:help "Disable interface";
					configd:update "/opt/vyatta/share/tmplscripts/interfaces/dataplane/vif/disable/configd_update.sh";
					configd:delete "/opt/vyatta/share/tmplscripts/interfaces/dataplane/vif/disable/configd_delete.sh";
				}
				leaf-list address {
					type if:address-dhcp;
					ordered-by "user";
					configd:help "IP address";
					configd:create "/opt/vyatta/share/tmplscripts/interfaces/dataplane/vif/address/configd_create.sh";
					configd:allowed "/opt/vyatta/share/tmplscripts/interfaces/dataplane/vif/address/configd_allowed.sh";
					configd:validate "/opt/vyatta/share/tmplscripts/interfaces/dataplane/vif/address/configd_validate1.cli";
				}
				leaf disable-link-detect {
					type empty;
					configd:help "Ignore link state changes";
					configd:update "/opt/vyatta/share/tmplscripts/interfaces/dataplane/vif/disable-link-detect/configd_update.sh";
					configd:delete "/opt/vyatta/share/tmplscripts/interfaces/dataplane/vif/disable-link-detect/configd_delete.sh";
				}
				container bridge-group {
					presence "true";
					configd:priority "320";
					configd:help "Add this interface to a bridge group";
					configd:end "/opt/vyatta/share/tmplscripts/interfaces/dataplane/vif/bridge-group/configd_end.sh";
					leaf priority {
						type uint32 {
							range 0..63 {
								error-message "Port priority must be between 0-63";
							}
						}
						configd:help "Bridge port priority";
					}
					leaf bridge {
						type string {
							pattern "br[0-9]+" {
								configd:error-message "$VAR(@): not a valid name for a bridge";
							}
						}
						configd:help "Bridge group name";
						configd:allowed "/opt/vyatta/share/tmplscripts/interfaces/dataplane/vif/bridge-group/bridge/configd_allowed.sh";
						configd:validate "/opt/vyatta/share/tmplscripts/interfaces/dataplane/vif/bridge-group/bridge/configd_validate1.cli";
					}
					leaf cost {
						type uint32 {
							range 1..65535 {
								error-message "Bridge cost value must be between 1 and 65535";
							}
						}
						configd:help "Bridge port cost";
					}
				}
			}
			leaf sflow {
				type empty;
				configd:help "Enable/Disable sflow for interface";
				configd:delete "vplane-sflow.pl --cmd=disable --intf=$VAR(../@)";
				configd:update "vplane-sflow.pl --cmd=enable --intf=$VAR(../@)";
			}
			leaf-list address {
				type if:address-dhcp;
				ordered-by "user";
				configd:help "IP address";
				configd:create "/opt/vyatta/share/tmplscripts/interfaces/dataplane/address/configd_create.sh";
				configd:allowed "/opt/vyatta/share/tmplscripts/interfaces/dataplane/address/configd_allowed.sh";
				configd:validate "/opt/vyatta/share/tmplscripts/interfaces/dataplane/address/configd_validate1.cli";
			}
			leaf mac {
				type types:mac-address {
					configd:syntax "/opt/vyatta/share/tmplscripts/interfaces/dataplane/mac/configd_syntax1.cli";
				}
				configd:help "Media Access Control (MAC) address";
				configd:create "/opt/vyatta/share/tmplscripts/interfaces/dataplane/mac/configd_create.sh";
			}
			leaf disable-link-detect {
				type empty;
				configd:help "Ignore link state changes";
				configd:create "/opt/vyatta/share/tmplscripts/interfaces/dataplane/disable-link-detect/configd_create.sh";
				configd:delete "/opt/vyatta/share/tmplscripts/interfaces/dataplane/disable-link-detect/configd_delete.sh";
			}
			container bridge-group {
				presence "true";
				configd:help "Add this interface to a bridge group";
				configd:end "/opt/vyatta/share/tmplscripts/interfaces/dataplane/bridge-group/configd_end.sh";
				leaf priority {
					type uint32 {
						range 0..63 {
							error-message "Port priority must be between 0-63";
						}
					}
					configd:help "Bridge port priority";
				}
				leaf root-block {
					type empty;
					configd:help "Enable Spanning Tree Protocol root guard";
				}
				leaf bpdu-guard {
					type empty;
					configd:help "Enable Spaning Tree Protocol BPDU guard";
				}
				leaf bridge {
					type string {
						pattern "br[0-9]+" {
							configd:error-message "$VAR(@): not a valid name for a bridge";
						}
					}
					configd:help "Bridge group name";
					configd:allowed "/opt/vyatta/share/tmplscripts/interfaces/dataplane/bridge-group/bridge/configd_allowed.sh";
					configd:validate "/opt/vyatta/share/tmplscripts/interfaces/dataplane/bridge-group/bridge/configd_validate1.cli";
				}
				leaf cost {
					type uint32 {
						range 1..65535 {
							error-message "Bridge cost value must be between 1 and 65535";
						}
					}
					configd:help "Bridge port cost";
				}
			}
		}
	}
}
