/***********************************************************************
 * brocade-vrrp.yang: Brocade VRRP data model
 *
 * March 2010, Hasan Raza, Karthik Rao
 *
 * Copyright (c) 2011 by Brocade Communications Systems, Inc.
 * All rights reserved.
 *
 **********************************************************************/
module brocade-vrrp {
    namespace "urn:brocade.com:mgmt:brocade-vrrp";
    prefix "vrrp";

    import brocade-rbridge {
        prefix rbridge; 
    }

    import brocade-interface { 
        prefix interface;
    }

    import tailf-common { 
        prefix tailf; 
    }

    import ietf-inet-types { 
        prefix inet; 
    }
    organization
        "Brocade Communications Systems, Inc.";

    contact
        "Brocade Communications Systems, Inc.
         Postal: 1745 Technology Drive,
                 San Jose, CA 95110
                  U.S.A
         Tel: +1-408-392-6061
         E-mail: support@Brocade.com
         web: www.brocade.com.";

    description
         "This module describes the data model for Virtual Router Redundancy Protocol";

    reference
         "RFC 3768 'Virtual Router Redundancy Protocol (VRRP)' and 
          RFC 2787 'Definitions of Managed Objects for the Virtual Router Redundancy Protocol'";

    revision "2011-10-31" {
        description     
            "Initial version of this management module.";
    }

    typedef vrid-type {
        type uint8 {
            range "1..255" {
                description "Virtual router identifier, Range: 1-255";
            }
        }
    }

    typedef version-num {
        type enumeration {
            enum v2 {
                value 2;
                description "Version 2";
            }
            enum v3 {
                value 3;
                description "Version 3";
            }
        }
    }

    typedef track-iftype {
        type enumeration {
            enum gigabitethernet {
                value 0;
                description "Gigabit Ethernet interface";
             }
            enum tengigabitethernet {
                value 1;
                description "TenGigabit Ethernet interface";
             }
            enum fortygigabitethernet {
                value 2;
                description "FortyGigabit Ethernet interface";
             }
            enum port-channel {
                value 3;
                description "Port-channel interface"; 
             }
            enum hundredgigabitethernet {
                value 10;
                description "HundredGigabit Ethernet interface";
             }
        }
    }

    typedef track-ifname {
        type union {
            type interface:interface-type { 
            }
            type string {
                pattern '([1-9]|[1-9][0-9]|[1-9][0-9]{2}|[1-5][0-9]{3}|'
                        + '6[0-1][0-4]{2})';
            }
        }
    }

    grouping global-vrrp-cmds {
        container hide-vrrp-holder {
            leaf vrrp {
                type empty;
                description "Virtual Router Redundacy Protocol (VRRP)";
            }
            leaf vrrp-extended {
                type empty;
                    description "Virtual Router Redundacy Protocol Extended (VRRP-E)";
            }
       }
    }

    grouping vrrp-interface-cmds {
        list vrrp {
            description "Start VRRP configuration";
            key "vrid version";
            leaf vrid {
                type vrid-type;
            }

            leaf version{
                //type version-num;
                  type uint8 {
                       range "2..3" {
                            }
                        }
            }

			leaf use-v2-checksum {
				type empty;
            	description "Enables v2 checksum computation method for VRRPv3 session";
			}

            list virtual-ip {
                key virtual-ipaddr;
                leaf virtual-ipaddr {
                    type inet:ipv4-address;
                    description "Virtual IPv4 address in dotted decimal";
                }
            }
      
            container track {
                description "Interface to be tracked";

                list interface {
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrp-groups;
        }
 
        /*list virtual-gateway {
            key vrid;
            leaf vrid {
                type vrid-type;
            }
            uses vrrp-vcs-cmds;
        }*/
    }

	container protocol-vrrp {
        description 
            "An intermediary node that separates the protocol vrrp from other protocols.";
        container protocol {
        }
    }

    augment "/rbridge:rbridge-id/interface:protocol" {
        	uses global-vrrp-cmds;
		}
    
    grouping vrrpe-cmds-only {
        leaf advertise-backup {
            type empty;
            description "Enable periodic backup advertisement messages";
        }

        leaf vrrpe-garp-timer {
            type uint32 {
                range "0..3600";
            }
        }

        leaf backup-advertisement-interval {
            type uint32 {
                range "60..3600" {
                }
            }
            default 60;
            description "Set Backup advertisement interval";
        }

        container short-path-forwarding {
            description "Enable backup router to send traffic";
			
            leaf basic {
                type empty;
            }

			leaf revert-priority {
				type uint8 {
					range "1..254" {
					}
				}
            	description "Set revert priority";
			}
        }

        leaf advertisement-interval-scale {
            type uint32 {
                range "1..10" {
                }
            }
            description "Ipv4 session advertisement interval scale factor";

        }

    }

    grouping vrrp-vcs-cmds {
        leaf priority {
            type uint8 {
                range "1..254" {
                }
            }
            default 100;
            description "Set router priority within virtual router";
        }
    
        leaf description {
            type string {
                length "1..64" {
                    description "Characters describing this interface (Max Size - 64)";
                }
            }
            description "Interface specific description";
        }
    }

    grouping vrrp-groups {
        leaf advertisement-interval {
            type uint32 {
				range "1..40900" {
                }
			}
            description "1-255(sec) for VRRPv2, VRRPE and 100-40900(mili sec) for VRRPv3";
        }

/*
		container enable {
			presence "enable";
            description "Enable Session";

			leaf enable-flag {
                type empty;
                description "Enable Session";
			}
	    }
*/	    
        leaf enable {
            type empty;
            description "Enable Session";
        }

        leaf hold-time {
            type uint32 {
                range "1..3600" {
                }
            }
            description "Configure hold time for this session";
        }

        leaf preempt-mode {
            type empty;
            description "Set preempt mode for the session";
        }
		container arp {
            description "Modify ARP requests";

    		container unicast-request {
                description "Modify Unicast ARP requests";

	    		leaf receive {
                    type empty;
                    description "Receive unicast ARP requests";
			    }
	        }
        }
        uses vrrp-vcs-cmds;
    }

    augment /interface:interface/interface:tengigabitethernet {
        uses vrrp-interface-cmds;
    }
    
    augment /interface:interface/interface:gigabitethernet {
        uses vrrp-interface-cmds;
    }
    
    augment /interface:interface/interface:fortygigabitethernet {
        uses vrrp-interface-cmds;
    }

    augment /interface:interface/interface:hundredgigabitethernet {
        uses vrrp-interface-cmds;
    }

    augment /rbridge:rbridge-id/interface:interface/interface:ve {
        list vrrp {
            key "vrid version";
            leaf vrid {
                type vrid-type;
            }

            leaf version{
//                type version-num;
                  type uint8 {
                       range "2..3" {
                            }
                       }
            }

			leaf use-v2-checksum {
				type empty;
            	description "Enables v2 checksum computation method for VRRPv3 session";
			}

            list virtual-ip {
                key virtual-ipaddr;
                leaf virtual-ipaddr {
                    type inet:ipv4-address;
                    description "Virtual IPv4 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }

            uses vrrp-groups;
        }

        list vrrpe {
//            tailf:cli-full-command;
            key vrid;
            leaf vrid {
                type vrid-type;
            }

			leaf virtual-mac {
				description "Virtual MAC";

				type enumeration {
					enum 02e0.5200.00xx {
						value 1;
					}
				}
			}

            list virtual-ip {
                key virtual-ipaddr;
                leaf virtual-ipaddr {
                    type inet:ipv4-address;
                    description "Virtual IPv4 address";
                }
            }
      
            container track {
//                tailf:callpoint vrrpe_track_vlan;
                description "Interface to be tracked";

                list network {
                    //tailf:cli-drop-node-name;

                    key "network-address";
                    leaf network-address {
                          type inet:ipv4-prefix;
                          description "IPv4 global address";
                        }

                    leaf network-priority {
                        type uint8 {
                            range "1..254" {
                        }
                    }
                }

                }

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }

            uses vrrp-groups;
            uses vrrpe-cmds-only;
        }

        /*list virtual-gateway {
            //tailf:callpoint vrrp_vcs_session_vlanintf;
            key vrid;
            leaf vrid {
                type vrid-type;
            }
            uses vrrp-vcs-cmds;
        }*/
    }

    // grouping cause yang compiler to crash, forced to duplicate 
    /*augment "/interface:interface-vlan/interface:interface/interface:ve" {
        list vrrp {
            key "vrid version";
            leaf vrid {
                type vrid-type;
            }

            leaf version{
                  type uint8 {
                       range "2..3" {
                            }
                            }
            }

            list virtual-ip {
                key virtual-ipaddr;
                leaf virtual-ipaddr {
                    type inet:ipv4-address;
                    description "Virtual IPv4 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrp-groups;
        }

        list vrrpe {
            key vrid;
            leaf vrid {
                type vrid-type;
            }


            list virtual-ip {
                key virtual-ipaddr;
                leaf virtual-ipaddr {
                    type inet:ipv4-address;
                    description "Virtual IPv4 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrp-groups;
            uses vrrpe-cmds-only;
        }

        list virtual-gateway {
            key vrid;
            leaf vrid {
                type vrid-type;
            }
            uses vrrp-vcs-cmds;
        }
    }*/

    augment /interface:interface/interface:port-channel {
        container hide-vrrp-holer {
        
        list vrrp {
            key "vrid version";
            leaf vrid {
                type vrid-type;
            }

            leaf version{
//                type version-num;
                  type uint8 {
                       range "2..3" {
                            }
                            }
            }

            list virtual-ip {
                key virtual-ipaddr;
                leaf virtual-ipaddr {
                    type inet:ipv4-address;
                    description "Virtual IPv4 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrp-groups;
        }

        /*list virtual-gateway {
            //tailf:callpoint vrrp_vcs_session_pointf;
            key vrid;
            leaf vrid {
                type vrid-type;
            }
            uses vrrp-vcs-cmds;
        }*/
        }
    }
}
