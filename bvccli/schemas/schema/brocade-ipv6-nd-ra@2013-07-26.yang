/***********************************************************************
 * brocade-ipv6-nd-ra.yang: Brocade IPv6 Neighbour Discovery and  Router Advertisement data model.
 *
 * Aug 2013, Ruchi Prashar
 *
 * Copyright (c) 2013 by Brocade Communications Systems, Inc.
 * All rights reserved.
 *
 **********************************************************************/

module brocade-ipv6-nd-ra {

    namespace "urn:brocade.com:mgmt:brocade-ipv6-nd-ra";
    
    prefix ipv6-nd-ra;

    import brocade-rbridge { 
    	prefix rbridge; 
    }
    
    import brocade-interface { 
    	prefix interface;
    }
    
     import brocade-ipv6-config { 
    	prefix ipv6-config;
    }
    
    import ietf-inet-types  {
     	prefix "inet";
    }
    
    import brocade-common-def {
    	prefix common-def; 
    }
    
    import brocade-intf-loopback {
    	prefix intf-loopback;
    }
    
    import tailf-common {
    	prefix tailf;
    }
	
	import brocade-vcs {
		prefix "vcs";
	}
	
	/*import ietf-yang-types {
		prefix yang; 
	}*/
	
    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "This management sub-module contains the configuration
        for Neighbor Discovery and Router Advertisement.";

    revision "2013-07-26" {
        description     
            "Initial version of this management module.";
    }         


    typedef macAddr {
    	type string;
    }
    
    typedef neighbor-ipv6-address {
        type inet:ipv6-address;
    }
    
    /*** TYPE DEFINITIONS ***/
	grouping intf-ipv6-nd-ra 
	{
	
		container ipv6-intf-cmds
		{
			
			            //vrrp cmd

            leaf vrrp-suppress-interface-ra {
                type empty;
            }
			
			container nd 
			{
				
				//RA cmds
				
				leaf managed-config-flag {
					type empty;
				}
						
				leaf other-config-flag {
					type empty;
				}
				
				leaf broadcast-mac-trap {
					type empty;
				}

				leaf ra-lifetime {
					default 1800;
					type common-def:time-interval-sec {
						range "0..9000" {
						}
					}
				}
				
				leaf reachable-time {
					default 0;
					type common-def:time-interval-msec {
						range "0..3600000" {
						}
					}
				}
				
				leaf mtu {
					default 1500;
					type uint32 {
						range "1280..65535" {
						}
					}
				}
				
				leaf retrans-timer {
					default 0;
					type common-def:time-interval-msec {
						range "0..4294967295" {
						}
					}
				}
				
				leaf hoplimit {
					default 64;
					type uint32 {
						range "0..255" {
						}
					}
				}
				
				//ND cmd
				
				leaf ns-interval {
					default 1;
					type common-def:time-interval-sec {
						range "1..5" {
						}
					}
				}
				
				leaf proxy {
					type empty;
				}
				
				//ND cmd done
				
				
				//RA container level cmds
				
				container suppress-ra {
					
					leaf suppress-ra-flag {
						type empty;
					}
					
					leaf suppress-ra-mtu {
						type empty;
					}
					
					leaf suppress-ra-all	{
						type empty;
					}
				}
						
				container ra-interval {
					
					leaf max-interval {								
						//default 600;
						type common-def:time-interval-sec {
							range "4..1800" {
							}
						}
					}
					
					leaf min {
						//default 200;
						type common-def:time-interval-sec {
							range "4..1800" {
							}
						}
					}
				}
				
				//RA container level cmds done
				
				//ND container level cmds 
				container dad {
					
					leaf attempts {
						default 2;
						type uint32 {
							range "0..10" {
								}
						}
					}
					
					leaf time {
						default 1;
						type common-def:time-interval-sec {
							range "1..5" {
							}
						}
					}
				}
				

				container nud {
					
					container retry {
						
						leaf base {
							default 1;
							type int32 {
								range "1 .. 3" {
								}
							}
						}
						
						leaf interval {
							default 1000;
							type common-def:time-interval-msec {
								range "1000..36000000" {
								}
							}
						}
						
						leaf max-attempts {
							default 1;
							type int32 {
								range "0..600" {
								}
							}
						} 
					
					}
				}
				
				
				
				//ipv6 nd cache expire  expire-time-in-seconds [refresh] 
				container cache {
					
					leaf expire {
						default 14400;
						type common-def:time-interval-sec {
							range "30..14400" {
							}
						}
					}
				}
				
				//ND cmds done
				
				//prefix cmd 
				list prefix {
            		
            		key "prefix-ipv6-address";
            		leaf prefix-ipv6-address {
                		type inet:ipv6-prefix;	
            		}
            		
            		uses prefix-cmds;
				} 
				
			}
			
			list neighbor {

				key "ipv6-address";
				leaf ipv6-address {
					type neighbor-ipv6-address;
				}
				
				leaf hardware-address {
					//type yang:mac-address;
					type macAddr;
				}
			}
			
		}
 	}
 	
 	
 	// ND Prefix cmd
 	grouping prefix-cmds {
	
	  container lifetime {
					
 		choice ch-valid-type {
 						
			case ca-no-advertise {
				leaf no-advertise {
					type empty;
				}
			}
 			
			case ca-valid-lifetime {
				leaf valid-lifetime {
					default 0;
					type common-def:time-interval-sec {
					range "0..4294967295" {
						}
					}
				}
			}
			
			case ca-valid-infinite {
				leaf valid-infinite {
					type empty;
				}
			}
		}
		
		container preferred {
		    
			choice ch-preferred-type {
				
				case ca-preferred-lifetime {
					leaf preferred-lifetime {
						default 0;
						type common-def:time-interval-sec {
						range "0..4294967295" {
							}
						}
					}
				}
				
				case ca-preferred-infinite {
					leaf preferred-infinite {
						type empty;
					}
				}
			}
		
			
			container prefix-flags {
				
				leaf no-autoconfig {
					type empty;
				}
                
				leaf no-onlink {
				    type empty;
				}
			
				leaf off-link {
				    type empty;
				}
			}
		}
	  }
 	}
 	
 	
	//ND Global cmds
	grouping ipv6-globalNdRa {
	
		container ipv6-global-cmds
		{

			container nd-global {
				container dad {
					
					leaf global-dad-time {
						default 1;
						type common-def:time-interval-sec {
							range "1..5" {
							}
						}
					}
				}
			}
		}
	}

	
	augment "/rbridge:rbridge-id/rbridge:ipv6" {
		when '/vcs:vcsmode/vcs:vcs-mode = "true"';
		uses ipv6-globalNdRa;
	}
	
    grouping intf-phy-ipv6-nd-ra {
		container ipv6-nd-ra {

			uses intf-ipv6-nd-ra {
				refine "ipv6-intf-cmds/nd/prefix" {
               }
			
				refine "ipv6-intf-cmds/neighbor" {
               }
            }
		}
    }
    
	grouping intf-vlan-ipv6-nd-ra {
		container ipv6-nd-ra {
			
			uses intf-ipv6-nd-ra {
				refine "ipv6-intf-cmds/nd/prefix" {
               }
               	refine "ipv6-intf-cmds/neighbor" {
               }
			}
		}
    }

    grouping loopback-intf-ipv6-nd-ra {
        container ipv6-nd-ra {
			
			uses intf-ipv6-nd-ra {
				refine "ipv6-intf-cmds/nd/prefix" {
               }
                refine "ipv6-intf-cmds/neighbor" {
               }
			}
        }
    }

    augment "/interface:interface/interface:tengigabitethernet/interface:ipv6" {
        		uses intf-phy-ipv6-nd-ra;
    }

	augment "/interface:interface/interface:fortygigabitethernet/interface:ipv6" {
            	uses intf-phy-ipv6-nd-ra;
	}

	augment "/interface:interface/interface:gigabitethernet/interface:ipv6" {
            	uses intf-phy-ipv6-nd-ra;
	}
    augment "/interface:interface/interface:hundredgigabitethernet/interface:ipv6" {
        uses intf-phy-ipv6-nd-ra;
    }
    augment "/rbridge:rbridge-id/interface:interface/interface:ve/ipv6-config:ipv6" {
            uses intf-vlan-ipv6-nd-ra;
    }
    
}
