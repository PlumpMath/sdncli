module vyatta-policy-pbr {
	namespace "urn:vyatta.com:mgmt:vyatta-policy-pbr";
	prefix policy-pbr;

	import vyatta-interfaces {
		prefix if;
	}
	import vyatta-interfaces-dataplane {
		prefix interfaces-dataplane;
	}
	import vyatta-interfaces-l2tpeth {
		prefix interfaces-l2tpeth;
	}
	import vyatta-policy {
		prefix policy;
	}
	import vyatta-policy-route {
		prefix policy-route;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /policy:policy/policy-route:route {
		list pbr {
			configd:priority "310";
			configd:help "PBR group";
			configd:delete "/opt/vyatta/share/tmplscripts/policy/route/pbr/configd_delete.sh";
			configd:begin "/opt/vyatta/share/tmplscripts/policy/route/pbr/configd_begin.sh";
			configd:end "/opt/vyatta/share/tmplscripts/policy/route/pbr/configd_end.sh";
			key "tagnode";
			leaf tagnode {
				type string {
					pattern "[0-9A-Za-z][-_0-9A-Za-z]*" {
						error-message "only alpha-numeric policy name allowed";
					}
				}
				configd:help "PBR group";
			}
			leaf description {
				type string;
				configd:help "Rule-set description";
			}
			list rule {
				configd:help "Rule number (1-9999)";
				configd:end "/opt/vyatta/share/tmplscripts/policy/route/pbr/rule/configd_end.sh";
				configd:validate "/opt/vyatta/share/tmplscripts/policy/route/pbr/rule/configd_validate1.cli";
				key "tagnode";
				leaf tagnode {
					type uint32 {
						range 1..9999;
						configd:syntax "/opt/vyatta/share/tmplscripts/policy/route/pbr/rule/configd_syntax1.cli";
						configd:syntax "/opt/vyatta/share/tmplscripts/policy/route/pbr/rule/configd_syntax2.cli";
					}
					configd:help "Rule number (1-9999)";
				}
				container tcp {
					presence "true";
					configd:help "TCP flags to match";
					configd:validate "/opt/vyatta/share/tmplscripts/policy/route/pbr/rule/tcp/configd_validate1.cli";
					leaf flags {
						type string {
							pattern "(((!?(SYN|ACK|FIN|RST|PSH|URG),)*(!?(SYN|ACK|FIN|RST|PSH|URG))))" {
								error-message "Invalid value for TCP flags. Allowed values : SYN ACK FIN RST URG PSH
When specifying more than one flag, flags should be comma-separated.
For example : value of 'SYN,!ACK,!FIN,!RST' will only match packets with
the SYN flag set, and the ACK, FIN and RST flags unset";
							}
						}
						configd:help "TCP flags to match";
						configd:comp_help "/opt/vyatta/share/tmplscripts/policy/route/pbr/rule/tcp/flags/configd_comp_help.txt";
					}
				}
				container icmp {
					presence "true";
					configd:help "ICMP for IPV4";
					configd:validate "/opt/vyatta/share/tmplscripts/policy/route/pbr/rule/icmp/configd_validate1.cli";
					leaf type-name {
						type string {
							configd:syntax "/opt/vyatta/share/tmplscripts/policy/route/pbr/rule/icmp/type-name/configd_syntax1.cli";
						}
						configd:help "ICMP type-name";
						configd:allowed "/opt/vyatta/share/tmplscripts/policy/route/pbr/rule/icmp/type-name/configd_allowed.sh";
					}
					leaf code {
						type uint32 {
							range 0..255;
						}
						configd:help "ICMP code must be between 0 and 255";
						configd:validate "/opt/vyatta/share/tmplscripts/policy/route/pbr/rule/icmp/code/configd_validate1.cli";
						configd:validate "/opt/vyatta/share/tmplscripts/policy/route/pbr/rule/icmp/code/configd_validate2.cli";
					}
					leaf type {
						type uint32 {
							range 0..255;
						}
						configd:help "ICMP type must be between 0 and 255";
						configd:validate "/opt/vyatta/share/tmplscripts/policy/route/pbr/rule/icmp/type/configd_validate1.cli";
						configd:validate "/opt/vyatta/share/tmplscripts/policy/route/pbr/rule/icmp/type/configd_validate2.cli";
					}
				}
				leaf description {
					type string;
					configd:help "Rule description";
				}
				leaf action {
					type enumeration {
						enum "accept";
						enum "drop";
					}
					configd:help "Rule action";
				}
				leaf disable {
					type empty;
					configd:help "Disable PBR rule";
					configd:create "/opt/vyatta/share/tmplscripts/policy/route/pbr/rule/disable/configd_create.sh";
					configd:delete "/opt/vyatta/share/tmplscripts/policy/route/pbr/rule/disable/configd_delete.sh";
				}
				container icmpv6 {
					presence "true";
					configd:help "ICMP for IPV6";
					configd:validate "/opt/vyatta/share/tmplscripts/policy/route/pbr/rule/icmpv6/configd_validate1.cli";
					leaf type-name {
						type string {
							configd:syntax "/opt/vyatta/share/tmplscripts/policy/route/pbr/rule/icmpv6/type-name/configd_syntax1.cli";
						}
						configd:help "ICMPv6 type/code names";
						configd:allowed "/opt/vyatta/share/tmplscripts/policy/route/pbr/rule/icmpv6/type-name/configd_allowed.sh";
					}
					leaf code {
						type uint32 {
							range 0..255;
						}
						configd:help "ICMP code must be between 0 and 255";
						configd:validate "/opt/vyatta/share/tmplscripts/policy/route/pbr/rule/icmpv6/code/configd_validate1.cli";
						configd:validate "/opt/vyatta/share/tmplscripts/policy/route/pbr/rule/icmpv6/code/configd_validate2.cli";
					}
					leaf type {
						type uint32 {
							range 0..255;
						}
						configd:help "ICMP type must be between 0 and 255";
						configd:validate "/opt/vyatta/share/tmplscripts/policy/route/pbr/rule/icmpv6/type/configd_validate1.cli";
						configd:validate "/opt/vyatta/share/tmplscripts/policy/route/pbr/rule/icmpv6/type/configd_validate2.cli";
					}
				}
				container source {
					presence "true";
					configd:help "Source parameters";
					leaf address {
						type string {
                                                        configd:syntax "/opt/vyatta/share/tmplscripts/policy/route/pbr/rule/source/address/configd_syntax1.cli";
                                                        configd:syntax "/opt/vyatta/share/tmplscripts/policy/route/pbr/rule/source/address/configd_syntax2.cli";
                                                }
						configd:help "Source IP address, subnet, or address-group";
						configd:allowed "/opt/vyatta/share/tmplscripts/policy/route/pbr/rule/source/address/configd_allowed.sh";
						configd:validate "/opt/vyatta/share/tmplscripts/policy/route/pbr/rule/source/address/configd_validate1.cli";
						configd:validate "/opt/vyatta/share/tmplscripts/policy/route/pbr/rule/source/address/configd_validate2.cli";
						configd:validate "/opt/vyatta/share/tmplscripts/policy/route/pbr/rule/source/address/configd_validate3.cli";
						configd:validate "/opt/vyatta/share/tmplscripts/policy/route/pbr/rule/source/address/configd_validate4.cli";
						configd:validate "/opt/vyatta/share/tmplscripts/policy/route/pbr/rule/source/address/configd_validate5.cli";
						configd:validate "/opt/vyatta/share/tmplscripts/policy/route/pbr/rule/source/address/configd_validate6.cli";
					}
					leaf port {
						type string;
						configd:help "Source port or port-group";
						configd:allowed "/opt/vyatta/share/tmplscripts/policy/route/pbr/rule/source/port/configd_allowed.sh";
						configd:validate "/opt/vyatta/share/tmplscripts/policy/route/pbr/rule/source/port/configd_validate1.cli";
						configd:validate "/opt/vyatta/share/tmplscripts/policy/route/pbr/rule/source/port/configd_validate2.cli";
					}
				}
				leaf log {
					type empty;
					configd:help "Enable logging for PBR rule";
				}
				leaf table {
					type uint32 {
						range 1..128;
					}
					configd:help "Policy Based Routing Table id";
				}
				leaf address-family {
					type string {
						configd:syntax "/opt/vyatta/share/tmplscripts/policy/route/pbr/rule/address-family/configd_syntax1.cli";
					}
					configd:help "Address Family ipv4 or ipv6 for this ruleset";
				}
				container destination {
					presence "true";
					configd:help "Destination parameters";
					leaf address {
						type string {
							configd:syntax "/opt/vyatta/share/tmplscripts/policy/route/pbr/rule/destination/address/configd_syntax1.cli";
							configd:syntax "/opt/vyatta/share/tmplscripts/policy/route/pbr/rule/destination/address/configd_syntax2.cli";
						}
						configd:help "Destination IP address, subnet, or address-group";
						configd:validate "/opt/vyatta/share/tmplscripts/policy/route/pbr/rule/destination/address/configd_validate1.cli";
						configd:validate "/opt/vyatta/share/tmplscripts/policy/route/pbr/rule/destination/address/configd_validate2.cli";
						configd:validate "/opt/vyatta/share/tmplscripts/policy/route/pbr/rule/destination/address/configd_validate3.cli";
						configd:validate "/opt/vyatta/share/tmplscripts/policy/route/pbr/rule/destination/address/configd_validate4.cli";
						configd:validate "/opt/vyatta/share/tmplscripts/policy/route/pbr/rule/destination/address/configd_validate5.cli";
					}
					leaf port {
						type string;
						configd:help "Destination port or port-group";
						configd:allowed "/opt/vyatta/share/tmplscripts/policy/route/pbr/rule/destination/port/configd_allowed.sh";
						configd:validate "/opt/vyatta/share/tmplscripts/policy/route/pbr/rule/destination/port/configd_validate1.cli";
						configd:validate "/opt/vyatta/share/tmplscripts/policy/route/pbr/rule/destination/port/configd_validate2.cli";
					}
				}
				leaf dscp {
					type uint32 {
						range 0..63;
					}
					configd:help "DSCP value to match in an incoming IP header";
				}
				leaf protocol {
					type string {
						configd:syntax "/opt/vyatta/share/tmplscripts/policy/route/pbr/rule/protocol/configd_syntax1.cli";
					}
					configd:help "Protocol to match (name,  number or \"all\")";
					configd:allowed "/opt/vyatta/share/tmplscripts/policy/route/pbr/rule/protocol/configd_allowed.sh";
				}
			}
			leaf config-trap {
				type enumeration {
					enum "enable" {
						configd:help "Enable sending SNMP trap on firewall configuration change";
					}
					enum "disable" {
						configd:help "Disable sending SNMP trap on firewall configuration change";
					}
				}
				configd:help "SNMP trap generation on firewall configuration changes";
				default "disable";
			}
		}
	}
	augment /if:interfaces/interfaces-dataplane:dataplane {
		container policy {
			presence "true";
			configd:help "PBR Options";
                        configd:end "/opt/vyatta/share/tmplscripts/interfaces/dataplane/policy/configd_end.sh";
			leaf-list route {
				type string {
					pattern "[!-~]{1,28}" {
						error-message "PBR name must be 28 characters or less";
					}
					pattern "[^\|;&$<>]*" {
						error-message "PBR rule set name cannot contain shell punctuation";
					}
				}
				ordered-by "user";
				configd:help "Ruleset for PBR routed packets on inbound interface";
				configd:allowed "/opt/vyatta/share/tmplscripts/interfaces/dataplane/policy/route/configd_allowed.sh";
				configd:validate "/opt/vyatta/share/tmplscripts/interfaces/dataplane/policy/route/configd_validate1.cli";
			}
		}
	}
	augment /if:interfaces/interfaces-dataplane:dataplane/interfaces-dataplane:vif {
		container policy {
			presence "true";
			leaf-list route {
				type string {
					pattern "[!-~]{1,28}" {
						error-message "PBR name must be 28 characters or less";
					}
					pattern "[^-]" {
						error-message "PBR rule set name cannot start with \"-\"";
					}
					pattern "[^\|;&$<>]*" {
						error-message "PBR rule set name cannot contain shell punctuation";
					}
				}
				ordered-by "user";
				configd:help "Ruleset for PBR routed packets on inbound interface";
				configd:allowed "/opt/vyatta/share/tmplscripts/interfaces/dataplane/vif/policy/route/configd_allowed.sh";
				configd:validate "/opt/vyatta/share/tmplscripts/interfaces/dataplane/vif/policy/route/configd_validate1.cli";
			}
		}
	}
	augment /if:interfaces/interfaces-l2tpeth:l2tpeth {
		container policy {
			presence "true";
			leaf-list route {
				type string {
					pattern "[!-~]{1,28}" {
						error-message "PBR name must be 28 characters or less";
					}
					pattern "[^-]" {
						error-message "PBR rule set name cannot start with \"-\"";
					}
					pattern "[^\|;&$<>]*" {
						error-message "PBR rule set name cannot contain shell punctuation";
					}
				}
				ordered-by "user";
				configd:help "Ruleset for PBR routed packets on inbound interface";
				configd:allowed "/opt/vyatta/share/tmplscripts/interfaces/l2tpeth/policy/route/configd_allowed.sh";
				configd:validate "/opt/vyatta/share/tmplscripts/interfaces/l2tpeth/policy/route/configd_validate1.cli";
			}
		}
	}
	augment /if:interfaces/interfaces-l2tpeth:l2tpeth/interfaces-l2tpeth:vif {
		container policy {
			presence "true";
			leaf-list route {
				type string {
					pattern "[!-~]{1,28}" {
						error-message "PBR name must be 28 characters or less";
					}
					pattern "[^-]" {
						error-message "PBR rule set name cannot start with \"-\"";
					}
					pattern "[^\|;&$<>]*" {
						error-message "PBR rule set name cannot contain shell punctuation";
					}
				}
				ordered-by "user";
				configd:help "Ruleset for PBR routed packets on inbound interface";
				configd:allowed "/opt/vyatta/share/tmplscripts/interfaces/l2tpeth/vif/policy/route/configd_allowed.sh";
				configd:validate "/opt/vyatta/share/tmplscripts/interfaces/l2tpeth/vif/policy/route/configd_validate1.cli";
			}
		}
	}
}
