module vyatta-system-package {
	namespace "urn:vyatta.com:mgmt:vyatta-system-package";
	prefix system-package;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /system:system {
		container package {
			presence "true";
			configd:priority "400";
			configd:help "Package update repository parameters";
			leaf auto-sync {
				type uint32 {
					range 0..31 {
						error-message "auto-sync must be between 0 and 32 days";
					}
				}
				default "1";
				configd:help "Update the the repository cache every n days (0 disables auto-update)";
				configd:update "/opt/vyatta/share/tmplscripts/system/package/auto-sync/configd_update1.cli";
				configd:delete "/opt/vyatta/share/tmplscripts/system/package/auto-sync/configd_delete1.cli";
			}
			list repository {
				configd:help "Debian archive name";
				configd:end "/opt/vyatta/share/tmplscripts/system/package/repository/configd_end.sh";
				configd:validate "/opt/vyatta/share/tmplscripts/system/package/repository/configd_validate1.cli";
				configd:validate "/opt/vyatta/share/tmplscripts/system/package/repository/configd_validate2.cli";
				key "tagnode";
				leaf tagnode {
					type string;
					configd:help "Debian archive name";
				}
				leaf description {
					type string;
					configd:help "Repository description";
				}
				leaf password {
					type string {
						pattern "[^!]*" {
							error-message "Do not use '!' in url";
						}
					}
					configd:secret "true";
					configd:help "Repository password";
					default "";
				}
				leaf username {
					type string {
						pattern "[^!]*" {
							error-message "Do not use '!' in url";
						}
					}
					configd:help "Repository username";
					default "";
				}
				leaf url {
					type string {
						pattern "[^!]+" {
							error-message "URL must not be null and must not contain '!'";
						}
					}
					configd:help "Repository URL";
				}
				leaf components {
					type string {
						pattern "[^!]+" {
							error-message "Do not use '!' in component name";
						}
					}
					configd:help "Repository component names";
				}
				leaf distribution {
					type string {
						pattern "[^!]+" {
							error-message "Do not use '!' in distribution name";
						}
					}
					configd:help "Distribution name";
				}
			}
		}
	}
}
