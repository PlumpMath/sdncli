module vyatta-protocols-ospf {
	namespace "urn:vyatta.com:mgmt:vyatta-protocols-ospf";
	prefix protocols-ospf;

	import vyatta-protocols {
		prefix protocols;
	}
	import vyatta-types {
		prefix types;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}
	import vyatta-interfaces-vti {
		prefix interfaces-vti;
	}

	organization "Brocade Communications Systems, Inc.";
	contact
		"Brocade Communications Systems, Inc.
		 Postal: 130 Holger Way
		         San Jose, CA 95134
		 E-mail: support@Brocade.com
		 Web: www.brocade.com";

	revision 2014-11-07 {
		description "Update for 3.2.1R2";
	}
	
	revision 2014-10-28 {
		description "Update for 3.2.1R1";
	}
	
	revision 2014-09-08 {
		description "Initial revision.";
		configd:migration 1;
	}

	augment /protocols:protocols {
		container ospf {
			presence "true";
			configd:priority "620";
			configd:help "Open Shortest Path First protocol (OSPF) parameters";
			configd:begin "/opt/vyatta/share/tmplscripts/protocols/ospf/configd_begin.sh";
			configd:end "/opt/vyatta/share/tmplscripts/protocols/ospf/configd_end.sh";
			container parameters {
				presence "true";
				configd:help "OSPF specific parameters";
				leaf opaque-lsa {
					type empty;
					configd:help "Enable the Opaque-LSA capability (rfc2370)";
					configd:create "/opt/vyatta/share/tmplscripts/protocols/ospf/parameters/opaque-lsa/configd_create1.cli";
					configd:delete "/opt/vyatta/share/tmplscripts/protocols/ospf/parameters/opaque-lsa/configd_delete1.cli";
				}
				leaf abr-type {
					type enumeration {
						enum "cisco" {
							configd:help "Cisco ABR type (default)";
						}
						enum "ibm" {
							configd:help "Ibm ABR type";
						}
						enum "shortcut" {
							configd:help "Shortcut ABR type";
						}
						enum "standard" {
							configd:help "Standard ABR type";
						}
					}
					configd:help "OSPF ABR type";
					default "cisco";
					configd:update "/opt/vyatta/share/tmplscripts/protocols/ospf/parameters/abr-type/configd_update.sh";
					configd:delete "/opt/vyatta/share/tmplscripts/protocols/ospf/parameters/abr-type/configd_delete.sh";
				}
				leaf router-id {
					type types:ipv4-address;
					configd:help "Override the default router identifier";
				}
				leaf rfc1583-compatibility {
					type empty;
					configd:help "Enable rfc1583 criteria for handling AS external routes";
					configd:create "/opt/vyatta/share/tmplscripts/protocols/ospf/parameters/rfc1583-compatibility/configd_create1.cli";
					configd:delete "/opt/vyatta/share/tmplscripts/protocols/ospf/parameters/rfc1583-compatibility/configd_delete1.cli";
				}
			}
			list distribute-list {
				configd:help "Access list to filter networks in routing updates";
				key "tagnode";
				leaf tagnode {
					type uint32 {
						configd:syntax "/opt/vyatta/share/tmplscripts/protocols/ospf/distribute-list/configd_syntax1.cli";
					}
					configd:help "Access list to filter networks in routing updates";
				}
				leaf-list export {
					type enumeration {
						enum "bgp";
						enum "connected";
						enum "kernel";
						enum "rip";
						enum "static";
					}
					ordered-by "user";
					configd:help "Filter for outgoing routing updates [REQUIRED]";
					configd:create "/opt/vyatta/share/tmplscripts/protocols/ospf/distribute-list/export/configd_create.sh";
					configd:delete "/opt/vyatta/share/tmplscripts/protocols/ospf/distribute-list/export/configd_delete.sh";
					configd:validate "/opt/vyatta/share/tmplscripts/protocols/ospf/distribute-list/export/configd_validate1.cli";
					configd:validate "/opt/vyatta/share/tmplscripts/protocols/ospf/distribute-list/export/configd_validate2.cli";
				}
				leaf import {
					type empty;
					configd:help "Filter for incoming routing updates";
					configd:create "/opt/vyatta/share/tmplscripts/protocols/ospf/distribute-list/import/configd_create.sh";
					configd:delete "/opt/vyatta/share/tmplscripts/protocols/ospf/distribute-list/import/configd_delete.sh";
					configd:validate "/opt/vyatta/share/tmplscripts/protocols/ospf/distribute-list/import/configd_validate1.cli";
				}
			}
			leaf-list passive-interface {
				type string;
				ordered-by "user";
				configd:help "Suppress routing updates on an interface";
				configd:allowed "/opt/vyatta/share/tmplscripts/protocols/ospf/passive-interface/configd_allowed.sh";
				configd:create "/opt/vyatta/share/tmplscripts/protocols/ospf/passive-interface/configd_create.sh";
				configd:delete "/opt/vyatta/share/tmplscripts/protocols/ospf/passive-interface/configd_delete.sh";
			}
			leaf default-metric {
				type uint32 {
					range 1..16777214 {
						error-message "Must be between 1-16777214";
					}
				}
				configd:help "Metric of redistributed routes";
				configd:update "/opt/vyatta/share/tmplscripts/protocols/ospf/default-metric/configd_update1.cli";
				configd:delete "/opt/vyatta/share/tmplscripts/protocols/ospf/default-metric/configd_delete1.cli";
			}
			container refresh {
				presence "true";
				configd:help "Adjust refresh parameters";
				leaf timers {
					type uint32 {
						range 10..1800 {
							error-message "must be between 10-1800";
						}
					}
					configd:help "Refresh timer";
					configd:update "/opt/vyatta/share/tmplscripts/protocols/ospf/refresh/timers/configd_update.sh";
					configd:delete "/opt/vyatta/share/tmplscripts/protocols/ospf/refresh/timers/configd_delete.sh";
				}
			}
			list neighbor {
				configd:help "Neighbor IP address";
				configd:begin "/opt/vyatta/share/tmplscripts/protocols/ospf/neighbor/configd_begin.sh";
				configd:delete "/opt/vyatta/share/tmplscripts/protocols/ospf/neighbor/configd_delete.sh";
				key "tagnode";
				leaf tagnode {
					type types:ipv4-address;
					configd:help "Neighbor IP address";
				}
				leaf priority {
					type uint32 {
						range 0..255 {
							error-message "Priority must be between 0-255";
						}
					}
					configd:help "Neighbor priority in seconds";
					default "0";
				}
				leaf poll-interval {
					type uint32 {
						range 1..65535 {
							error-message "Must be between 1-65535 seconds";
						}
					}
					configd:help "Dead neighbor polling interval";
					default "60";
				}
			}
			container redistribute {
				presence "true";
				configd:help "Redistribute information from another routing protocol";
				container bgp {
					presence "true";
					configd:help "Redistribute BGP routes";
					configd:create "/opt/vyatta/share/tmplscripts/protocols/ospf/redistribute/bgp/configd_create.cli";
					configd:delete "/opt/vyatta/share/tmplscripts/protocols/ospf/redistribute/bgp/configd_delete.cli";
					leaf metric-type {
						type uint32 {
							range 1..2 {
								error-message "metric must be either 1 or 2";
							}
						}
						configd:help "OSPF metric type";
					        default "2";
					        configd:create "/opt/vyatta/share/tmplscripts/protocols/ospf/redistribute/bgp/metric-type/configd_create.cli";
					        configd:delete "/opt/vyatta/share/tmplscripts/protocols/ospf/redistribute/bgp/metric-type/configd_delete.cli";
					}
					leaf route-map {
						type string;
						configd:help "Route map reference";
						configd:allowed "/opt/vyatta/share/tmplscripts/protocols/ospf/redistribute/bgp/route-map/configd_allowed.sh";
						configd:validate "/opt/vyatta/share/tmplscripts/protocols/ospf/redistribute/bgp/route-map/configd_validate1.cli";
					        configd:create "/opt/vyatta/share/tmplscripts/protocols/ospf/redistribute/bgp/route-map/configd_create.cli";
					        configd:delete "/opt/vyatta/share/tmplscripts/protocols/ospf/redistribute/bgp/route-map/configd_delete.cli";
					}
					leaf metric {
						type uint32 {
							range 1..16777214 {
								error-message "metric must be between 1 and 16777214";
							}
						}
						configd:help "Metric for redistributed routes";
					        configd:create "/opt/vyatta/share/tmplscripts/protocols/ospf/redistribute/bgp/metric/configd_create.cli";
					        configd:delete "/opt/vyatta/share/tmplscripts/protocols/ospf/redistribute/bgp/metric/configd_delete.cli";
					}
				}
				container kernel {
					presence "true";
					configd:help "Redistribute kernel routes";
					configd:create "/opt/vyatta/share/tmplscripts/protocols/ospf/redistribute/kernel/configd_create.cli";
					configd:delete "/opt/vyatta/share/tmplscripts/protocols/ospf/redistribute/kernel/configd_delete.cli";
					leaf metric-type {
						type uint32 {
							range 1..2 {
								error-message "metric must be either 1 or 2";
							}
						}
						configd:help "OSPF metric type";
					        default "2";
					        configd:create "/opt/vyatta/share/tmplscripts/protocols/ospf/redistribute/kernel/metric-type/configd_create.cli";
					        configd:delete "/opt/vyatta/share/tmplscripts/protocols/ospf/redistribute/kernel/metric-type/configd_delete.cli";
					}
					leaf route-map {
						type string;
						configd:help "Route map reference";
						configd:allowed "/opt/vyatta/share/tmplscripts/protocols/ospf/redistribute/kernel/route-map/configd_allowed.sh";
						configd:validate "/opt/vyatta/share/tmplscripts/protocols/ospf/redistribute/kernel/route-map/configd_validate1.cli";
					        configd:create "/opt/vyatta/share/tmplscripts/protocols/ospf/redistribute/kernel/route-map/configd_create.cli";
					        configd:delete "/opt/vyatta/share/tmplscripts/protocols/ospf/redistribute/kernel/route-map/configd_delete.cli";
					}
					leaf metric {
						type uint32 {
							range 1..16777214 {
								error-message "metric must be between 1 and 16777214";
							}
						}
						configd:help "Metric for redistributed routes";
					        configd:create "/opt/vyatta/share/tmplscripts/protocols/ospf/redistribute/kernel/metric/configd_create.cli";
					        configd:delete "/opt/vyatta/share/tmplscripts/protocols/ospf/redistribute/kernel/metric/configd_delete.cli";
					}
				}
				container rip {
					presence "true";
					configd:help "Redistribute RIP routes";
					configd:create "/opt/vyatta/share/tmplscripts/protocols/ospf/redistribute/rip/configd_create.cli";
					configd:delete "/opt/vyatta/share/tmplscripts/protocols/ospf/redistribute/rip/configd_delete.cli";
					leaf metric-type {
						type uint32 {
							range 1..2 {
								error-message "metric must be either 1 or 2";
							}
						}
						configd:help "OSPF metric type";
					        default "2";
					        configd:create "/opt/vyatta/share/tmplscripts/protocols/ospf/redistribute/rip/metric-type/configd_create.cli";
					        configd:delete "/opt/vyatta/share/tmplscripts/protocols/ospf/redistribute/rip/metric-type/configd_delete.cli";
					}
					leaf route-map {
						type string;
						configd:help "Route map reference";
						configd:allowed "/opt/vyatta/share/tmplscripts/protocols/ospf/redistribute/rip/route-map/configd_allowed.sh";
						configd:validate "/opt/vyatta/share/tmplscripts/protocols/ospf/redistribute/rip/route-map/configd_validate1.cli";
					        configd:create "/opt/vyatta/share/tmplscripts/protocols/ospf/redistribute/rip/route-map/configd_create.cli";
					        configd:delete "/opt/vyatta/share/tmplscripts/protocols/ospf/redistribute/rip/route-map/configd_delete.cli";
					}
					leaf metric {
						type uint32 {
							range 1..16777214 {
								error-message "metric must be between 1 and 16777214";
							}
						}
						configd:help "Metric for redistributed routes";
					        configd:create "/opt/vyatta/share/tmplscripts/protocols/ospf/redistribute/rip/metric/configd_create.cli";
					        configd:delete "/opt/vyatta/share/tmplscripts/protocols/ospf/redistribute/rip/metric/configd_delete.cli";
					}
				}
				container connected {
					presence "true";
					configd:help "Redistribute connected routes";
					configd:create "/opt/vyatta/share/tmplscripts/protocols/ospf/redistribute/connected/configd_create.cli";
					configd:delete "/opt/vyatta/share/tmplscripts/protocols/ospf/redistribute/connected/configd_delete.cli";
					leaf metric-type {
						type uint32 {
							range 1..2 {
								error-message "metric must be either 1 or 2";
							}
						}
						configd:help "OSPF metric type";
					        default "2";
					        configd:create "/opt/vyatta/share/tmplscripts/protocols/ospf/redistribute/connected/metric-type/configd_create.cli";
					        configd:delete "/opt/vyatta/share/tmplscripts/protocols/ospf/redistribute/connected/metric-type/configd_delete.cli";
					}
					leaf route-map {
						type string;
						configd:help "Route map reference";
						configd:allowed "/opt/vyatta/share/tmplscripts/protocols/ospf/redistribute/connected/route-map/configd_allowed.sh";
						configd:validate "/opt/vyatta/share/tmplscripts/protocols/ospf/redistribute/connected/route-map/configd_validate1.cli";
					        configd:create "/opt/vyatta/share/tmplscripts/protocols/ospf/redistribute/connected/route-map/configd_create.cli";
					        configd:delete "/opt/vyatta/share/tmplscripts/protocols/ospf/redistribute/connected/route-map/configd_delete.cli";
					}
					leaf metric {
						type uint32 {
							range 1..16777214 {
								error-message "metric must be between 1 and 16777214";
							}
						}
						configd:help "Metric for redistributed routes";
					        configd:create "/opt/vyatta/share/tmplscripts/protocols/ospf/redistribute/connected/metric/configd_create.cli";
					        configd:delete "/opt/vyatta/share/tmplscripts/protocols/ospf/redistribute/connected/metric/configd_delete.cli";
					}
				}
				container static {
					presence "true";
					configd:help "Redistribute static routes";
					configd:create "/opt/vyatta/share/tmplscripts/protocols/ospf/redistribute/static/configd_create.cli";
					configd:delete "/opt/vyatta/share/tmplscripts/protocols/ospf/redistribute/static/configd_delete.cli";
					leaf metric-type {
						type uint32 {
							range 1..2 {
								error-message "metric must be either 1 or 2";
							}
						}
						configd:help "OSPF metric type";
					        default "2";
					        configd:create "/opt/vyatta/share/tmplscripts/protocols/ospf/redistribute/static/metric-type/configd_create.cli";
					        configd:delete "/opt/vyatta/share/tmplscripts/protocols/ospf/redistribute/static/metric-type/configd_delete.cli";
					}
					leaf route-map {
						type string;
						configd:help "Route map reference";
						configd:allowed "/opt/vyatta/share/tmplscripts/protocols/ospf/redistribute/static/route-map/configd_allowed.sh";
						configd:validate "/opt/vyatta/share/tmplscripts/protocols/ospf/redistribute/static/route-map/configd_validate1.cli";
					        configd:create "/opt/vyatta/share/tmplscripts/protocols/ospf/redistribute/static/route-map/configd_create.cli";
					        configd:delete "/opt/vyatta/share/tmplscripts/protocols/ospf/redistribute/static/route-map/configd_delete.cli";
					}
					leaf metric {
						type uint32 {
							range 1..16777214 {
								error-message "metric must be between 1 and 16777214";
							}
						}
						configd:help "Metric for redistributed routes";
					        configd:create "/opt/vyatta/share/tmplscripts/protocols/ospf/redistribute/static/metric/configd_create.cli";
					        configd:delete "/opt/vyatta/share/tmplscripts/protocols/ospf/redistribute/static/metric/configd_delete.cli";
					}
				}
			}
			container distance {
				presence "true";
				configd:help "Administrative distance";
				leaf global {
					type uint32 {
						range 1..255 {
							error-message "Must be between 1-255";
						}
					}
					configd:help "OSPF administrative distance";
					configd:create "/opt/vyatta/share/tmplscripts/protocols/ospf/distance/global/configd_create.cli";
					configd:delete "/opt/vyatta/share/tmplscripts/protocols/ospf/distance/global/configd_delete.cli";
				}
				container ospf {
					presence "true";
					configd:help "OSPF administrative distance";
					configd:delete "/opt/vyatta/share/tmplscripts/protocols/ospf/distance/ospf/configd_delete.cli";
					leaf external {
						type uint32 {
							range 1..255 {
								error-message "Must be between 1-255";
							}
						}
						configd:help "Distance for external routes";
						configd:create "/opt/vyatta/share/tmplscripts/protocols/ospf/distance/ospf/external/configd_create.cli";
						configd:delete "/opt/vyatta/share/tmplscripts/protocols/ospf/distance/ospf/external/configd_delete.cli";
					}
					leaf inter-area {
						type uint32 {
							range 1..255 {
								error-message "Must be between 1-255";
							}
						}
						configd:help "Distance for inter-area routes";
						configd:create "/opt/vyatta/share/tmplscripts/protocols/ospf/distance/ospf/inter-area/configd_create.cli";
						configd:delete "/opt/vyatta/share/tmplscripts/protocols/ospf/distance/ospf/inter-area/configd_delete.cli";
					}
					leaf intra-area {
						type uint32 {
							range 1..255 {
								error-message "Must be between 1-255";
							}
						}
						configd:help "Distance for intra-area routes";
						configd:create "/opt/vyatta/share/tmplscripts/protocols/ospf/distance/ospf/intra-area/configd_create.cli";
						configd:delete "/opt/vyatta/share/tmplscripts/protocols/ospf/distance/ospf/intra-area/configd_delete.cli";
					}
				}
			}
			list summary-address {
				configd:help "Summary network and mask";
				configd:create "/opt/vyatta/share/tmplscripts/protocols/ospf/summary-address/configd_create1.cli";
				key "tagnode";
				leaf tagnode {
					type types:ipv4-prefix;
					configd:help "Summary network and mask";
				}
				leaf tag {
					type uint32 {
						range 0..max {
							error-message "Tag must be between 0-4294967295";
						}
					}
					configd:help "OSPF tag identifier for summary address.";
					configd:create "/opt/vyatta/share/tmplscripts/protocols/ospf/summary-address/tag/configd_create.sh";
					configd:delete "/opt/vyatta/share/tmplscripts/protocols/ospf/summary-address/tag/configd_delete.sh";
				}
				leaf advertise {
					type empty;
					configd:help "Summary address to be advertised.";
					configd:create "/opt/vyatta/share/tmplscripts/protocols/ospf/summary-address/advertise/configd_create.sh";
					configd:delete "/opt/vyatta/share/tmplscripts/protocols/ospf/summary-address/advertise/configd_delete.sh";
				}
				leaf not-advertise {
					type empty;
					configd:help "Summary address which shouldn't be advertised.";
					configd:create "/opt/vyatta/share/tmplscripts/protocols/ospf/summary-address/not-advertise/configd_create.sh";
					configd:delete "/opt/vyatta/share/tmplscripts/protocols/ospf/summary-address/not-advertise/configd_delete.sh";
				}
			}
			container default-information {
				presence "true";
				configd:help "Control distribution of default information";
				container originate {
					presence "true";
					configd:help "Distribute a default route";
					configd:create "/opt/vyatta/share/tmplscripts/protocols/ospf/default-information/originate/configd_create.cli";
					configd:delete "/opt/vyatta/share/tmplscripts/protocols/ospf/default-information/originate/configd_delete.cli";
					leaf metric-type {
						type enumeration {
							enum "1";
							enum "2";
						}
						configd:help "OSPF metric type for default routes";
					        configd:create "/opt/vyatta/share/tmplscripts/protocols/ospf/default-information/originate/metric-type/configd_create.cli";
					        configd:delete "/opt/vyatta/share/tmplscripts/protocols/ospf/default-information/originate/metric-type/configd_delete.cli";
					}
					leaf always {
						type empty;
						configd:help "Always advertise default route";
					        configd:create "/opt/vyatta/share/tmplscripts/protocols/ospf/default-information/originate/always/configd_create.cli";
					        configd:delete "/opt/vyatta/share/tmplscripts/protocols/ospf/default-information/originate/always/configd_delete.cli";
					}
					leaf route-map {
						type string;
						configd:help "Route map reference";
						configd:allowed "/opt/vyatta/share/tmplscripts/protocols/ospf/default-information/originate/route-map/configd_allowed.sh";
						configd:validate "/opt/vyatta/share/tmplscripts/protocols/ospf/default-information/originate/route-map/configd_validate.cli";
					        configd:create "/opt/vyatta/share/tmplscripts/protocols/ospf/default-information/originate/route-map/configd_create.cli";
					        configd:delete "/opt/vyatta/share/tmplscripts/protocols/ospf/default-information/originate/route-map/configd_delete.cli";
					}
					leaf metric {
						type uint32 {
							range 0..16777214 {
								error-message "must be between 0-16777214";
							}
						}
						configd:help "OSPF default metric";
					        configd:create "/opt/vyatta/share/tmplscripts/protocols/ospf/default-information/originate/metric/configd_create.cli";
					        configd:delete "/opt/vyatta/share/tmplscripts/protocols/ospf/default-information/originate/metric/configd_delete.cli";
					}
				}
			}
			list area {
				configd:help "OSPF Area";
				key "tagnode";
				leaf tagnode {
					type union {
						type types:ipv4-address;
						type uint32;
					}
					configd:help "OSPF Area";
				}
				leaf authentication {
					type enumeration {
						enum "plaintext" {
							configd:help "Use plain-text authentication";
						}
						enum "md5" {
							configd:help "Use md5 authentication";
						}
					}
					configd:help "OSPF area authentication type";
					configd:allowed "/opt/vyatta/share/tmplscripts/protocols/ospf/area/authentication/configd_allowed.sh";
					configd:update "/opt/vyatta/share/tmplscripts/protocols/ospf/area/authentication/configd_update1.cli";
					configd:delete "/opt/vyatta/share/tmplscripts/protocols/ospf/area/authentication/configd_delete1.cli";
				}
				list virtual-link {
					configd:help "Virtual link";
					configd:create "/opt/vyatta/share/tmplscripts/protocols/ospf/area/virtual-link/configd_create1.cli";
					configd:delete "/opt/vyatta/share/tmplscripts/protocols/ospf/area/virtual-link/configd_delete1.cli";
					key "tagnode";
					leaf tagnode {
						type types:ipv4-address;
						configd:help "Virtual link";
					}
					container authentication {
						presence "true";
						configd:help "Authentication";
						leaf plaintext-password {
							type string {
								configd:syntax "/opt/vyatta/share/tmplscripts/protocols/ospf/area/virtual-link/authentication/plaintext-password/configd_syntax1.cli";
							}
							configd:secret "true";
							configd:help "Plain text password";
							configd:update "/opt/vyatta/share/tmplscripts/protocols/ospf/area/virtual-link/authentication/plaintext-password/configd_update.sh";
							configd:delete "/opt/vyatta/share/tmplscripts/protocols/ospf/area/virtual-link/authentication/plaintext-password/configd_delete.sh";
							configd:validate "/opt/vyatta/share/tmplscripts/protocols/ospf/area/virtual-link/authentication/plaintext-password/configd_validate1.cli";
						}
						leaf plaintext {
							type empty;
							configd:help "Plain text authentication";
							configd:update "/opt/vyatta/share/tmplscripts/protocols/ospf/area/virtual-link/authentication/plaintext/configd_update.sh";
							configd:delete "/opt/vyatta/share/tmplscripts/protocols/ospf/area/virtual-link/authentication/plaintext/configd_delete.sh";
							configd:validate "/opt/vyatta/share/tmplscripts/protocols/ospf/area/virtual-link/authentication/plaintext/configd_validate1.cli";
						}
						leaf md5 {
							type empty;
							configd:help "MD5 key id";
							configd:update "/opt/vyatta/share/tmplscripts/protocols/ospf/area/virtual-link/authentication/md5/configd_update.sh";
							configd:delete "/opt/vyatta/share/tmplscripts/protocols/ospf/area/virtual-link/authentication/md5/configd_delete.sh";
							configd:validate "/opt/vyatta/share/tmplscripts/protocols/ospf/area/virtual-link/authentication/md5/configd_validate1.cli";
						}
						list md5-key-id {
							configd:help "MD5 key id";
							configd:validate "/opt/vyatta/share/tmplscripts/protocols/ospf/area/virtual-link/authentication/md5-key-id/configd_validate1.cli";
							configd:create "/opt/vyatta/share/tmplscripts/protocols/ospf/area/virtual-link/authentication/md5-key-id/configd_create1.cli";
							configd:delete "/opt/vyatta/share/tmplscripts/protocols/ospf/area/virtual-link/authentication/md5-key-id/configd_delete1.cli";
							key "tagnode";
							leaf tagnode {
								type uint32 {
									range 1..255 {
										error-message "ID must be between (1-255)";
									}
								}
								configd:help "MD5 key id";
							}
							leaf md5-key {
								type string {
									configd:syntax "/opt/vyatta/share/tmplscripts/protocols/ospf/area/virtual-link/authentication/md5-key-id/md5-key/configd_syntax1.cli";
								}
								configd:help "MD5 key";
							}
						}
					}
					leaf dead-interval {
						type uint32 {
							range 1..65535 {
								error-message "Must be between 1-65535";
							}
						}
						configd:help "Interval after which a neighbor is declared dead";
						default "40";
						configd:update "/opt/vyatta/share/tmplscripts/protocols/ospf/area/virtual-link/dead-interval/configd_update1.cli";
						configd:delete "/opt/vyatta/share/tmplscripts/protocols/ospf/area/virtual-link/dead-interval/configd_delete1.cli";
					}
					leaf hello-interval {
						type uint32 {
							range 1..65535 {
								error-message "Must be between 1-65535";
							}
						}
						configd:help "Interval between hello packets";
						default "10";
						configd:update "/opt/vyatta/share/tmplscripts/protocols/ospf/area/virtual-link/hello-interval/configd_update1.cli";
						configd:delete "/opt/vyatta/share/tmplscripts/protocols/ospf/area/virtual-link/hello-interval/configd_delete1.cli";
					}
					leaf retransmit-interval {
						type uint32 {
							range 1..65535 {
								error-message "Must be between 1-65535";
							}
						}
						configd:help "Interval between retransmitting lost link state advertisements";
						default "5";
						configd:update "/opt/vyatta/share/tmplscripts/protocols/ospf/area/virtual-link/retransmit-interval/configd_update1.cli";
						configd:delete "/opt/vyatta/share/tmplscripts/protocols/ospf/area/virtual-link/retransmit-interval/configd_delete1.cli";
					}
					leaf transmit-delay {
						type uint32 {
							range 1..65535 {
								error-message "Must be between 1-65535";
							}
						}
						configd:help "Link state transmit delay";
						default "1";
						configd:update "/opt/vyatta/share/tmplscripts/protocols/ospf/area/virtual-link/transmit-delay/configd_update1.cli";
						configd:delete "/opt/vyatta/share/tmplscripts/protocols/ospf/area/virtual-link/transmit-delay/configd_delete1.cli";
					}
				}
				container area-type {
					presence "true";
					configd:help "Area type";
					container stub {
						presence "true";
						configd:help "Stub OSPF area";
						configd:create "/opt/vyatta/share/tmplscripts/protocols/ospf/area/area-type/stub/configd_create.sh";
						configd:delete "/opt/vyatta/share/tmplscripts/protocols/ospf/area/area-type/stub/configd_delete.sh";
						leaf default-cost {
							type uint32 {
								range 0..16777215 {
									error-message "Cost must be between 0-16777215";
								}
							}
							configd:help "Summary-default cost of stub area";
							configd:create "/opt/vyatta/share/tmplscripts/protocols/ospf/area/area-type/stub/default-cost/configd_create.sh";
							configd:update "/opt/vyatta/share/tmplscripts/protocols/ospf/area/area-type/stub/default-cost/configd_update.sh";
							configd:delete "/opt/vyatta/share/tmplscripts/protocols/ospf/area/area-type/stub/default-cost/configd_delete.sh";
						}
						leaf no-summary {
							type empty;
							configd:help "Do not inject inter-area routes into stub";
							configd:create "/opt/vyatta/share/tmplscripts/protocols/ospf/area/area-type/stub/no-summary/configd_create.sh";
							configd:delete "/opt/vyatta/share/tmplscripts/protocols/ospf/area/area-type/stub/no-summary/configd_delete.sh";
						}
					}
					container nssa {
						presence "true";
						configd:help "Nssa OSPF area";
						configd:create "/opt/vyatta/share/tmplscripts/protocols/ospf/area/area-type/nssa/configd_create.sh";
						configd:delete "/opt/vyatta/share/tmplscripts/protocols/ospf/area/area-type/nssa/configd_delete.sh";
						leaf default-cost {
							type uint32 {
								range 0..16777215 {
									error-message "Cost must be between 0-16777215";
								}
							}
							configd:help "Summary-default cost of nssa area";
							configd:create "/opt/vyatta/share/tmplscripts/protocols/ospf/area/area-type/nssa/default-cost/configd_create.sh";
							configd:update "/opt/vyatta/share/tmplscripts/protocols/ospf/area/area-type/nssa/default-cost/configd_update.sh";
							configd:delete "/opt/vyatta/share/tmplscripts/protocols/ospf/area/area-type/nssa/default-cost/configd_delete.sh";
						}
						container default-information-originate {
							presence "true";
							configd:help "Distribute a default route into an NSSA area";
							configd:create "/opt/vyatta/share/tmplscripts/protocols/ospf/area/area-type/nssa/default-information-originate/configd_create.sh";
							configd:delete "/opt/vyatta/share/tmplscripts/protocols/ospf/area/area-type/nssa/default-information-originate/configd_delete.sh";
							leaf metric-type {
								type enumeration {
									enum "1";
									enum "2";
								}
								configd:help "OSPF metric type for default routes";
								configd:create "/opt/vyatta/share/tmplscripts/protocols/ospf/area/area-type/nssa/default-information-originate/metric-type/configd_create.sh";
								configd:delete "/opt/vyatta/share/tmplscripts/protocols/ospf/area/area-type/nssa/default-information-originate/metric-type/configd_delete.sh";
							}
							leaf metric {
								type uint32 {
									range 0..16777214 {
										error-message "must be between 0-16777214";
									}
								}
								configd:help "OSPF default metric";
								configd:create "/opt/vyatta/share/tmplscripts/protocols/ospf/area/area-type/nssa/default-information-originate/metric/configd_create.sh";
								configd:delete "/opt/vyatta/share/tmplscripts/protocols/ospf/area/area-type/nssa/default-information-originate/metric/configd_delete.sh";
							}
						}
						leaf translate {
							type enumeration {
								enum "always" {
									configd:help "NSSA-ABR to always translate";
								}
								enum "candidate" {
									configd:help "NSSA-ABR for translate election (default)";
								}
							}
							configd:help "Nssa-abr";
							default "candidate";
							configd:create "/opt/vyatta/share/tmplscripts/protocols/ospf/area/area-type/nssa/translate/configd_create.sh";
							configd:update "/opt/vyatta/share/tmplscripts/protocols/ospf/area/area-type/nssa/translate/configd_update.sh";
							configd:delete "/opt/vyatta/share/tmplscripts/protocols/ospf/area/area-type/nssa/translate/configd_delete.sh";
						}
						leaf no-summary {
							type empty;
							configd:help "Do not inject inter-area routes into stub";
							configd:create "/opt/vyatta/share/tmplscripts/protocols/ospf/area/area-type/nssa/no-summary/configd_create.sh";
							configd:delete "/opt/vyatta/share/tmplscripts/protocols/ospf/area/area-type/nssa/no-summary/configd_delete.sh";
						}
					}
				}
				leaf shortcut {
					type enumeration {
						enum "default" {
							configd:help "Set default; ";
						}
						enum "disable" {
							configd:help "Disable shortcutting mode; ";
						}
						enum "enable" {
							configd:help "Enable  shortcutting mode; ";
						}
					}
					configd:help "Area's shortcut mode";
					configd:allowed "/opt/vyatta/share/tmplscripts/protocols/ospf/area/shortcut/configd_allowed.sh";
					configd:update "/opt/vyatta/share/tmplscripts/protocols/ospf/area/shortcut/configd_update1.cli";
					configd:delete "/opt/vyatta/share/tmplscripts/protocols/ospf/area/shortcut/configd_delete1.cli";
				}
				list range {
					configd:help "Summarize routes matching prefix (border routers only)";
					configd:end "/opt/vyatta/share/tmplscripts/protocols/ospf/area/range/configd_end.sh";
					key "tagnode";
					leaf tagnode {
						type types:ipv4-prefix {
							configd:syntax "/opt/vyatta/share/tmplscripts/protocols/ospf/area/range/configd_syntax1.cli";
						}
						configd:help "Summarize routes matching prefix (border routers only)";
					}
					leaf not-advertise {
						type empty;
						configd:help "Do not advertise this range";
					}
				}
				leaf-list network {
					type types:ipv4-prefix {
						configd:syntax "/opt/vyatta/share/tmplscripts/protocols/ospf/area/network/configd_syntax1.cli";
					}
					ordered-by "user";
					configd:help "OSPF network [REQUIRED]";
					configd:create "/opt/vyatta/share/tmplscripts/protocols/ospf/area/network/configd_create.sh";
					configd:delete "/opt/vyatta/share/tmplscripts/protocols/ospf/area/network/configd_delete.sh";
				}
			}
			container auto-cost {
				presence "true";
				configd:help "Calculate OSPF interface cost according to bandwidth";
				leaf reference-bandwidth {
					type uint32 {
						range 1..4294967 {
							error-message "Must be between 1-4294967";
						}
					}
					configd:help "Reference bandwidth method to assign OSPF cost";
					default "100";
					configd:update "/opt/vyatta/share/tmplscripts/protocols/ospf/auto-cost/reference-bandwidth/configd_update1.cli";
					configd:delete "/opt/vyatta/share/tmplscripts/protocols/ospf/auto-cost/reference-bandwidth/configd_delete1.cli";
				}
			}
			container overflow {
				presence "true";
				configd:help "Configure OSPF Overflow handling capabilities.";
				container database {
					presence "true";
					configd:help "configure type of ospf overflow protection";
					container hard {
						presence "true";
						configd:help "Hard limit on number of LSAs, instance will shut down if limit exceeded";
						leaf limit {
							type uint32 {
								range 0..4294967294 {
									error-message "must be between 0-4294967294";
								}
							}
							configd:help "Max LSAs in database.";
							configd:update "/opt/vyatta/share/tmplscripts/protocols/ospf/overflow/database/hard/limit/configd_update.sh";
							configd:delete "/opt/vyatta/share/tmplscripts/protocols/ospf/overflow/database/hard/limit/configd_delete.sh";
							configd:validate "/opt/vyatta/share/tmplscripts/protocols/ospf/overflow/database/hard/limit/configd_validate1.cli";
						}
					}
					container external {
						presence "true";
						configd:help "Max AS-External LSAs in database.";
						list limit {
							configd:help "Max LSAs in database.";
							configd:validate "/opt/vyatta/share/tmplscripts/protocols/ospf/overflow/database/external/limit/configd_validate1.cli";
							key "tagnode";
							leaf tagnode {
								type uint32 {
									range 0..2147483647 {
										error-message "must be between 0-2147483647";
									}
								}
								configd:help "Max LSAs in database.";
							}
							leaf recovery {
								type uint32 {
									range 0..65535 {
										error-message "must be between 0-65535";
									}
								}
								configd:help "Time to recover (0 implies no recovery)";
								configd:update "/opt/vyatta/share/tmplscripts/protocols/ospf/overflow/database/external/limit/recovery/configd_update.sh";
								configd:delete "/opt/vyatta/share/tmplscripts/protocols/ospf/overflow/database/external/limit/recovery/configd_delete.sh";
							}
						}
					}
					container soft {
						presence "true";
						configd:help "Soft limit on number of LSAs in database, will warn if exceeded";
						leaf limit {
							type uint32 {
								range 0..4294967294 {
									error-message "must be between 0-4294967294";
								}
							}
							configd:help "Max LSAs in database.";
							configd:update "/opt/vyatta/share/tmplscripts/protocols/ospf/overflow/database/soft/limit/configd_update.sh";
							configd:delete "/opt/vyatta/share/tmplscripts/protocols/ospf/overflow/database/soft/limit/configd_delete.sh";
							configd:validate "/opt/vyatta/share/tmplscripts/protocols/ospf/overflow/database/soft/limit/configd_validate1.cli";
						}
					}
				}
			}
		}
	}
	augment /if:interfaces/interfaces-bridge:bridge/interfaces-bridge:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/bridge/ip/ospf/priority/configd_update.sh";
				configd:delete "/opt/vyatta/share/tmplscripts/interfaces/bridge/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/bridge/ip/ospf/authentication/plaintext-password/configd_update.sh";
					configd:delete "/opt/vyatta/share/tmplscripts/interfaces/bridge/ip/ospf/authentication/plaintext-password/configd_delete.sh";
				}
				leaf plaintext {
					type empty;
					configd:help "Enable/disable plain text authentication";
					configd:update "/opt/vyatta/share/tmplscripts/interfaces/bridge/ip/ospf/authentication/plaintext/configd_update.sh";
					configd:delete "/opt/vyatta/share/tmplscripts/interfaces/bridge/ip/ospf/authentication/plaintext/configd_delete.sh";
				}
				leaf md5 {
					type empty;
					configd:help "MD5 parameters";
					configd:create "/opt/vyatta/share/tmplscripts/interfaces/bridge/ip/ospf/authentication/md5/configd_create.sh";
					configd:delete "/opt/vyatta/share/tmplscripts/interfaces/bridge/ip/ospf/authentication/md5/configd_delete.sh";
				}
				list md5-key-id {
					configd:help "MD5 key id";
					configd:validate "/opt/vyatta/share/tmplscripts/interfaces/bridge/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/bridge/ip/ospf/authentication/md5-key-id/md5-key/configd_create.sh";
						configd:update "/opt/vyatta/share/tmplscripts/interfaces/bridge/ip/ospf/authentication/md5-key-id/md5-key/configd_update.sh";
						configd:delete "/opt/vyatta/share/tmplscripts/interfaces/bridge/ip/ospf/authentication/md5-key-id/md5-key/configd_delete.sh";
					}
				}
			}
			leaf mtu-ignore {
				type empty;
				configd:help "Disable Maximum Transmission Unit (MTU) mismatch detection";
				configd:create "/opt/vyatta/share/tmplscripts/interfaces/bridge/ip/ospf/mtu-ignore/configd_create.sh";
				configd:delete "/opt/vyatta/share/tmplscripts/interfaces/bridge/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/bridge/ip/ospf/dead-interval/configd_update.sh";
				configd:delete "/opt/vyatta/share/tmplscripts/interfaces/bridge/ip/ospf/dead-interval/configd_delete.sh";
			}
			leaf hello-interval {
				type uint32 {
					range 1..65535 {
						error-message "Must be between 1-65535";
					}
				}
				configd:help "Interval between hello packets";
				configd:create "/opt/vyatta/share/tmplscripts/interfaces/bridge/ip/ospf/hello-interval/configd_create.sh";
				configd:delete "/opt/vyatta/share/tmplscripts/interfaces/bridge/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/bridge/ip/ospf/retransmit-interval/configd_update.sh";
				configd:delete "/opt/vyatta/share/tmplscripts/interfaces/bridge/ip/ospf/retransmit-interval/configd_delete.sh";
			}
			leaf cost {
				type uint32 {
					range 1..65535 {
						error-message "Must be between 1-65535";
					}
				}
				configd:help "Interface cost";
				configd:update "/opt/vyatta/share/tmplscripts/interfaces/bridge/ip/ospf/cost/configd_update.sh";
				configd:delete "/opt/vyatta/share/tmplscripts/interfaces/bridge/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/bridge/ip/ospf/network/configd_update.sh";
				configd:delete "/opt/vyatta/share/tmplscripts/interfaces/bridge/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/bridge/ip/ospf/transmit-delay/configd_update.sh";
				configd:delete "/opt/vyatta/share/tmplscripts/interfaces/bridge/ip/ospf/transmit-delay/configd_delete.sh";
			}
		}
	}
	augment /if:interfaces/interfaces-dataplane:dataplane/interfaces-dataplane:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/dataplane/ip/ospf/priority/configd_update.sh";
				configd:delete "/opt/vyatta/share/tmplscripts/interfaces/dataplane/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/dataplane/ip/ospf/authentication/plaintext-password/configd_update.sh";
					configd:delete "/opt/vyatta/share/tmplscripts/interfaces/dataplane/ip/ospf/authentication/plaintext-password/configd_delete.sh";
				}
				leaf plaintext {
					type empty;
					configd:help "Enable/disable plain text authentication";
					configd:update "/opt/vyatta/share/tmplscripts/interfaces/dataplane/ip/ospf/authentication/plaintext/configd_update.sh";
					configd:delete "/opt/vyatta/share/tmplscripts/interfaces/dataplane/ip/ospf/authentication/plaintext/configd_delete.sh";
				}
				leaf md5 {
					type empty;
					configd:help "MD5 parameters";
					configd:create "/opt/vyatta/share/tmplscripts/interfaces/dataplane/ip/ospf/authentication/md5/configd_create.sh";
					configd:delete "/opt/vyatta/share/tmplscripts/interfaces/dataplane/ip/ospf/authentication/md5/configd_delete.sh";
				}
				list md5-key-id {
					configd:help "MD5 key id";
					configd:validate "/opt/vyatta/share/tmplscripts/interfaces/dataplane/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/dataplane/ip/ospf/authentication/md5-key-id/md5-key/configd_create.sh";
						configd:update "/opt/vyatta/share/tmplscripts/interfaces/dataplane/ip/ospf/authentication/md5-key-id/md5-key/configd_update.sh";
						configd:delete "/opt/vyatta/share/tmplscripts/interfaces/dataplane/ip/ospf/authentication/md5-key-id/md5-key/configd_delete.sh";
					}
				}
			}
			leaf mtu-ignore {
				type empty;
				configd:help "Disable Maximum Transmission Unit (MTU) mismatch detection";
				configd:create "/opt/vyatta/share/tmplscripts/interfaces/dataplane/ip/ospf/mtu-ignore/configd_create.sh";
				configd:delete "/opt/vyatta/share/tmplscripts/interfaces/dataplane/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/dataplane/ip/ospf/dead-interval/configd_update.sh";
				configd:delete "/opt/vyatta/share/tmplscripts/interfaces/dataplane/ip/ospf/dead-interval/configd_delete.sh";
			}
			leaf hello-interval {
				type uint32 {
					range 1..65535 {
						error-message "Must be between 1-65535";
					}
				}
				configd:help "Interval between hello packets";
				configd:create "/opt/vyatta/share/tmplscripts/interfaces/dataplane/ip/ospf/hello-interval/configd_create.sh";
				configd:delete "/opt/vyatta/share/tmplscripts/interfaces/dataplane/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/dataplane/ip/ospf/retransmit-interval/configd_update.sh";
				configd:delete "/opt/vyatta/share/tmplscripts/interfaces/dataplane/ip/ospf/retransmit-interval/configd_delete.sh";
			}
			leaf cost {
				type uint32 {
					range 1..65535 {
						error-message "Must be between 1-65535";
					}
				}
				configd:help "Interface cost";
				configd:update "/opt/vyatta/share/tmplscripts/interfaces/dataplane/ip/ospf/cost/configd_update.sh";
				configd:delete "/opt/vyatta/share/tmplscripts/interfaces/dataplane/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/dataplane/ip/ospf/network/configd_update.sh";
				configd:delete "/opt/vyatta/share/tmplscripts/interfaces/dataplane/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/dataplane/ip/ospf/transmit-delay/configd_update.sh";
				configd:delete "/opt/vyatta/share/tmplscripts/interfaces/dataplane/ip/ospf/transmit-delay/configd_delete.sh";
			}
		}
	}
	augment /if:interfaces/interfaces-dataplane:dataplane/interfaces-dataplane:vif/interfaces-dataplane:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/dataplane/vif/ip/ospf/priority/configd_update.sh";
				configd:delete "/opt/vyatta/share/tmplscripts/interfaces/dataplane/vif/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/dataplane/vif/ip/ospf/authentication/plaintext-password/configd_update.sh";
					configd:delete "/opt/vyatta/share/tmplscripts/interfaces/dataplane/vif/ip/ospf/authentication/plaintext-password/configd_delete.sh";
				}
				leaf plaintext {
					type empty;
					configd:help "Enable/disable plain text authentication";
					configd:update "/opt/vyatta/share/tmplscripts/interfaces/dataplane/vif/ip/ospf/authentication/plaintext/configd_update.sh";
					configd:delete "/opt/vyatta/share/tmplscripts/interfaces/dataplane/vif/ip/ospf/authentication/plaintext/configd_delete.sh";
				}
				leaf md5 {
					type empty;
					configd:help "MD5 parameters";
					configd:create "/opt/vyatta/share/tmplscripts/interfaces/dataplane/vif/ip/ospf/authentication/md5/configd_create.sh";
					configd:delete "/opt/vyatta/share/tmplscripts/interfaces/dataplane/vif/ip/ospf/authentication/md5/configd_delete.sh";
				}
				list md5-key-id {
					configd:help "MD5 key id";
					configd:validate "/opt/vyatta/share/tmplscripts/interfaces/dataplane/vif/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/dataplane/vif/ip/ospf/authentication/md5-key-id/md5-key/configd_create.sh";
						configd:update "/opt/vyatta/share/tmplscripts/interfaces/dataplane/vif/ip/ospf/authentication/md5-key-id/md5-key/configd_update.sh";
						configd:delete "/opt/vyatta/share/tmplscripts/interfaces/dataplane/vif/ip/ospf/authentication/md5-key-id/md5-key/configd_delete.sh";
					}
				}
			}
			leaf mtu-ignore {
				type empty;
				configd:help "Disable Maximum Transmission Unit (MTU) mismatch detection";
				configd:create "/opt/vyatta/share/tmplscripts/interfaces/dataplane/vif/ip/ospf/mtu-ignore/configd_create.sh";
				configd:delete "/opt/vyatta/share/tmplscripts/interfaces/dataplane/vif/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/dataplane/vif/ip/ospf/dead-interval/configd_update.sh";
				configd:delete "/opt/vyatta/share/tmplscripts/interfaces/dataplane/vif/ip/ospf/dead-interval/configd_delete.sh";
			}
			leaf hello-interval {
				type uint32 {
					range 1..65535 {
						error-message "Must be between 1-65535";
					}
				}
				configd:help "Interval between hello packets";
				configd:create "/opt/vyatta/share/tmplscripts/interfaces/dataplane/vif/ip/ospf/hello-interval/configd_create.sh";
				configd:delete "/opt/vyatta/share/tmplscripts/interfaces/dataplane/vif/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/dataplane/vif/ip/ospf/retransmit-interval/configd_update.sh";
				configd:delete "/opt/vyatta/share/tmplscripts/interfaces/dataplane/vif/ip/ospf/retransmit-interval/configd_delete.sh";
			}
			leaf cost {
				type uint32 {
					range 1..65535 {
						error-message "Must be between 1-65535";
					}
				}
				configd:help "Interface cost";
				configd:update "/opt/vyatta/share/tmplscripts/interfaces/dataplane/vif/ip/ospf/cost/configd_update.sh";
				configd:delete "/opt/vyatta/share/tmplscripts/interfaces/dataplane/vif/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/dataplane/vif/ip/ospf/network/configd_update.sh";
				configd:delete "/opt/vyatta/share/tmplscripts/interfaces/dataplane/vif/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/dataplane/vif/ip/ospf/transmit-delay/configd_update.sh";
				configd:delete "/opt/vyatta/share/tmplscripts/interfaces/dataplane/vif/ip/ospf/transmit-delay/configd_delete.sh";
			}
		}
	}
	augment /if:interfaces/interfaces-l2tpeth:l2tpeth/interfaces-l2tpeth:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/l2tpeth/ip/ospf/priority/configd_update.sh";
				configd:delete "/opt/vyatta/share/tmplscripts/interfaces/l2tpeth/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/l2tpeth/ip/ospf/authentication/plaintext-password/configd_update.sh";
					configd:delete "/opt/vyatta/share/tmplscripts/interfaces/l2tpeth/ip/ospf/authentication/plaintext-password/configd_delete.sh";
				}
				leaf plaintext {
					type empty;
					configd:help "Enable/disable plain text authentication";
					configd:update "/opt/vyatta/share/tmplscripts/interfaces/l2tpeth/ip/ospf/authentication/plaintext/configd_update.sh";
					configd:delete "/opt/vyatta/share/tmplscripts/interfaces/l2tpeth/ip/ospf/authentication/plaintext/configd_delete.sh";
				}
				leaf md5 {
					type empty;
					configd:help "MD5 parameters";
					configd:create "/opt/vyatta/share/tmplscripts/interfaces/l2tpeth/ip/ospf/authentication/md5/configd_create.sh";
					configd:delete "/opt/vyatta/share/tmplscripts/interfaces/l2tpeth/ip/ospf/authentication/md5/configd_delete.sh";
				}
				list md5-key-id {
					configd:help "MD5 key id";
					configd:validate "/opt/vyatta/share/tmplscripts/interfaces/l2tpeth/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/l2tpeth/ip/ospf/authentication/md5-key-id/md5-key/configd_create.sh";
						configd:update "/opt/vyatta/share/tmplscripts/interfaces/l2tpeth/ip/ospf/authentication/md5-key-id/md5-key/configd_update.sh";
						configd:delete "/opt/vyatta/share/tmplscripts/interfaces/l2tpeth/ip/ospf/authentication/md5-key-id/md5-key/configd_delete.sh";
					}
				}
			}
			leaf mtu-ignore {
				type empty;
				configd:help "Disable Maximum Transmission Unit (MTU) mismatch detection";
				configd:create "/opt/vyatta/share/tmplscripts/interfaces/l2tpeth/ip/ospf/mtu-ignore/configd_create.sh";
				configd:delete "/opt/vyatta/share/tmplscripts/interfaces/l2tpeth/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/l2tpeth/ip/ospf/dead-interval/configd_update.sh";
				configd:delete "/opt/vyatta/share/tmplscripts/interfaces/l2tpeth/ip/ospf/dead-interval/configd_delete.sh";
			}
			leaf hello-interval {
				type uint32 {
					range 1..65535 {
						error-message "Must be between 1-65535";
					}
				}
				configd:help "Interval between hello packets";
				configd:create "/opt/vyatta/share/tmplscripts/interfaces/l2tpeth/ip/ospf/hello-interval/configd_create.sh";
				configd:delete "/opt/vyatta/share/tmplscripts/interfaces/l2tpeth/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/l2tpeth/ip/ospf/retransmit-interval/configd_update.sh";
				configd:delete "/opt/vyatta/share/tmplscripts/interfaces/l2tpeth/ip/ospf/retransmit-interval/configd_delete.sh";
			}
			leaf cost {
				type uint32 {
					range 1..65535 {
						error-message "Must be between 1-65535";
					}
				}
				configd:help "Interface cost";
				configd:update "/opt/vyatta/share/tmplscripts/interfaces/l2tpeth/ip/ospf/cost/configd_update.sh";
				configd:delete "/opt/vyatta/share/tmplscripts/interfaces/l2tpeth/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/l2tpeth/ip/ospf/network/configd_update.sh";
				configd:delete "/opt/vyatta/share/tmplscripts/interfaces/l2tpeth/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/l2tpeth/ip/ospf/transmit-delay/configd_update.sh";
				configd:delete "/opt/vyatta/share/tmplscripts/interfaces/l2tpeth/ip/ospf/transmit-delay/configd_delete.sh";
			}
		}
	}
	augment /if:interfaces/interfaces-l2tpeth:l2tpeth/interfaces-l2tpeth:vif/interfaces-l2tpeth:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/l2tpeth/vif/ip/ospf/priority/configd_update.sh";
				configd:delete "/opt/vyatta/share/tmplscripts/interfaces/l2tpeth/vif/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/l2tpeth/vif/ip/ospf/authentication/plaintext-password/configd_update.sh";
					configd:delete "/opt/vyatta/share/tmplscripts/interfaces/l2tpeth/vif/ip/ospf/authentication/plaintext-password/configd_delete.sh";
				}
				leaf plaintext {
					type empty;
					configd:help "Enable/disable plain text authentication";
					configd:update "/opt/vyatta/share/tmplscripts/interfaces/l2tpeth/vif/ip/ospf/authentication/plaintext/configd_update.sh";
					configd:delete "/opt/vyatta/share/tmplscripts/interfaces/l2tpeth/vif/ip/ospf/authentication/plaintext/configd_delete.sh";
				}
				leaf md5 {
					type empty;
					configd:help "MD5 parameters";
					configd:create "/opt/vyatta/share/tmplscripts/interfaces/l2tpeth/vif/ip/ospf/authentication/md5/configd_create.sh";
					configd:delete "/opt/vyatta/share/tmplscripts/interfaces/l2tpeth/vif/ip/ospf/authentication/md5/configd_delete.sh";
				}
				list md5-key-id {
					configd:help "MD5 key id";
					configd:validate "/opt/vyatta/share/tmplscripts/interfaces/l2tpeth/vif/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/l2tpeth/vif/ip/ospf/authentication/md5-key-id/md5-key/configd_create.sh";
						configd:update "/opt/vyatta/share/tmplscripts/interfaces/l2tpeth/vif/ip/ospf/authentication/md5-key-id/md5-key/configd_update.sh";
						configd:delete "/opt/vyatta/share/tmplscripts/interfaces/l2tpeth/vif/ip/ospf/authentication/md5-key-id/md5-key/configd_delete.sh";
					}
				}
			}
			leaf mtu-ignore {
				type empty;
				configd:help "Disable Maximum Transmission Unit (MTU) mismatch detection";
				configd:create "/opt/vyatta/share/tmplscripts/interfaces/l2tpeth/vif/ip/ospf/mtu-ignore/configd_create.sh";
				configd:delete "/opt/vyatta/share/tmplscripts/interfaces/l2tpeth/vif/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/l2tpeth/vif/ip/ospf/dead-interval/configd_update.sh";
				configd:delete "/opt/vyatta/share/tmplscripts/interfaces/l2tpeth/vif/ip/ospf/dead-interval/configd_delete.sh";
			}
			leaf hello-interval {
				type uint32 {
					range 1..65535 {
						error-message "Must be between 1-65535";
					}
				}
				configd:help "Interval between hello packets";
				configd:create "/opt/vyatta/share/tmplscripts/interfaces/l2tpeth/vif/ip/ospf/hello-interval/configd_create.sh";
				configd:delete "/opt/vyatta/share/tmplscripts/interfaces/l2tpeth/vif/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/l2tpeth/vif/ip/ospf/retransmit-interval/configd_update.sh";
				configd:delete "/opt/vyatta/share/tmplscripts/interfaces/l2tpeth/vif/ip/ospf/retransmit-interval/configd_delete.sh";
			}
			leaf cost {
				type uint32 {
					range 1..65535 {
						error-message "Must be between 1-65535";
					}
				}
				configd:help "Interface cost";
				configd:update "/opt/vyatta/share/tmplscripts/interfaces/l2tpeth/vif/ip/ospf/cost/configd_update.sh";
				configd:delete "/opt/vyatta/share/tmplscripts/interfaces/l2tpeth/vif/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/l2tpeth/vif/ip/ospf/network/configd_update.sh";
				configd:delete "/opt/vyatta/share/tmplscripts/interfaces/l2tpeth/vif/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/l2tpeth/vif/ip/ospf/transmit-delay/configd_update.sh";
				configd:delete "/opt/vyatta/share/tmplscripts/interfaces/l2tpeth/vif/ip/ospf/transmit-delay/configd_delete.sh";
			}
		}
	}
	augment /if:interfaces/interfaces-loopback:loopback/interfaces-loopback:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/loopback/ip/ospf/priority/configd_update.sh";
				configd:delete "/opt/vyatta/share/tmplscripts/interfaces/loopback/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/loopback/ip/ospf/authentication/plaintext-password/configd_update.sh";
					configd:delete "/opt/vyatta/share/tmplscripts/interfaces/loopback/ip/ospf/authentication/plaintext-password/configd_delete.sh";
				}
				leaf plaintext {
					type empty;
					configd:help "Enable/disable plain text authentication";
					configd:update "/opt/vyatta/share/tmplscripts/interfaces/loopback/ip/ospf/authentication/plaintext/configd_update.sh";
					configd:delete "/opt/vyatta/share/tmplscripts/interfaces/loopback/ip/ospf/authentication/plaintext/configd_delete.sh";
				}
				leaf md5 {
					type empty;
					configd:help "MD5 parameters";
					configd:create "/opt/vyatta/share/tmplscripts/interfaces/loopback/ip/ospf/authentication/md5/configd_create.sh";
					configd:delete "/opt/vyatta/share/tmplscripts/interfaces/loopback/ip/ospf/authentication/md5/configd_delete.sh";
				}
				list md5-key-id {
					configd:help "MD5 key id";
					configd:validate "/opt/vyatta/share/tmplscripts/interfaces/loopback/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/loopback/ip/ospf/authentication/md5-key-id/md5-key/configd_create.sh";
						configd:update "/opt/vyatta/share/tmplscripts/interfaces/loopback/ip/ospf/authentication/md5-key-id/md5-key/configd_update.sh";
						configd:delete "/opt/vyatta/share/tmplscripts/interfaces/loopback/ip/ospf/authentication/md5-key-id/md5-key/configd_delete.sh";
					}
				}
			}
			leaf mtu-ignore {
				type empty;
				configd:help "Disable Maximum Transmission Unit (MTU) mismatch detection";
				configd:create "/opt/vyatta/share/tmplscripts/interfaces/loopback/ip/ospf/mtu-ignore/configd_create.sh";
				configd:delete "/opt/vyatta/share/tmplscripts/interfaces/loopback/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/loopback/ip/ospf/dead-interval/configd_update.sh";
				configd:delete "/opt/vyatta/share/tmplscripts/interfaces/loopback/ip/ospf/dead-interval/configd_delete.sh";
			}
			leaf hello-interval {
				type uint32 {
					range 1..65535 {
						error-message "Must be between 1-65535";
					}
				}
				configd:help "Interval between hello packets";
				configd:create "/opt/vyatta/share/tmplscripts/interfaces/loopback/ip/ospf/hello-interval/configd_create.sh";
				configd:delete "/opt/vyatta/share/tmplscripts/interfaces/loopback/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/loopback/ip/ospf/retransmit-interval/configd_update.sh";
				configd:delete "/opt/vyatta/share/tmplscripts/interfaces/loopback/ip/ospf/retransmit-interval/configd_delete.sh";
			}
			leaf cost {
				type uint32 {
					range 1..65535 {
						error-message "Must be between 1-65535";
					}
				}
				configd:help "Interface cost";
				configd:update "/opt/vyatta/share/tmplscripts/interfaces/loopback/ip/ospf/cost/configd_update.sh";
				configd:delete "/opt/vyatta/share/tmplscripts/interfaces/loopback/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/loopback/ip/ospf/network/configd_update.sh";
				configd:delete "/opt/vyatta/share/tmplscripts/interfaces/loopback/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/loopback/ip/ospf/transmit-delay/configd_update.sh";
				configd:delete "/opt/vyatta/share/tmplscripts/interfaces/loopback/ip/ospf/transmit-delay/configd_delete.sh";
			}
		}
	}
	augment /if:interfaces/interfaces-openvpn:openvpn/interfaces-openvpn:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/openvpn/ip/ospf/priority/configd_update.sh";
				configd:delete "/opt/vyatta/share/tmplscripts/interfaces/openvpn/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/openvpn/ip/ospf/authentication/plaintext-password/configd_update.sh";
					configd:delete "/opt/vyatta/share/tmplscripts/interfaces/openvpn/ip/ospf/authentication/plaintext-password/configd_delete.sh";
				}
				leaf plaintext {
					type empty;
					configd:help "Enable/disable plain text authentication";
					configd:update "/opt/vyatta/share/tmplscripts/interfaces/openvpn/ip/ospf/authentication/plaintext/configd_update.sh";
					configd:delete "/opt/vyatta/share/tmplscripts/interfaces/openvpn/ip/ospf/authentication/plaintext/configd_delete.sh";
				}
				leaf md5 {
					type empty;
					configd:help "MD5 parameters";
					configd:create "/opt/vyatta/share/tmplscripts/interfaces/openvpn/ip/ospf/authentication/md5/configd_create.sh";
					configd:delete "/opt/vyatta/share/tmplscripts/interfaces/openvpn/ip/ospf/authentication/md5/configd_delete.sh";
				}
				list md5-key-id {
					configd:help "MD5 key id";
					configd:validate "/opt/vyatta/share/tmplscripts/interfaces/openvpn/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/openvpn/ip/ospf/authentication/md5-key-id/md5-key/configd_create.sh";
						configd:update "/opt/vyatta/share/tmplscripts/interfaces/openvpn/ip/ospf/authentication/md5-key-id/md5-key/configd_update.sh";
						configd:delete "/opt/vyatta/share/tmplscripts/interfaces/openvpn/ip/ospf/authentication/md5-key-id/md5-key/configd_delete.sh";
					}
				}
			}
			leaf mtu-ignore {
				type empty;
				configd:help "Disable Maximum Transmission Unit (MTU) mismatch detection";
				configd:create "/opt/vyatta/share/tmplscripts/interfaces/openvpn/ip/ospf/mtu-ignore/configd_create.sh";
				configd:delete "/opt/vyatta/share/tmplscripts/interfaces/openvpn/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/openvpn/ip/ospf/dead-interval/configd_update.sh";
				configd:delete "/opt/vyatta/share/tmplscripts/interfaces/openvpn/ip/ospf/dead-interval/configd_delete.sh";
			}
			leaf hello-interval {
				type uint32 {
					range 1..65535 {
						error-message "Must be between 1-65535";
					}
				}
				configd:help "Interval between hello packets";
				configd:create "/opt/vyatta/share/tmplscripts/interfaces/openvpn/ip/ospf/hello-interval/configd_create.sh";
				configd:delete "/opt/vyatta/share/tmplscripts/interfaces/openvpn/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/openvpn/ip/ospf/retransmit-interval/configd_update.sh";
				configd:delete "/opt/vyatta/share/tmplscripts/interfaces/openvpn/ip/ospf/retransmit-interval/configd_delete.sh";
			}
			leaf cost {
				type uint32 {
					range 1..65535 {
						error-message "Must be between 1-65535";
					}
				}
				configd:help "Interface cost";
				configd:update "/opt/vyatta/share/tmplscripts/interfaces/openvpn/ip/ospf/cost/configd_update.sh";
				configd:delete "/opt/vyatta/share/tmplscripts/interfaces/openvpn/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/openvpn/ip/ospf/network/configd_update.sh";
				configd:delete "/opt/vyatta/share/tmplscripts/interfaces/openvpn/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/openvpn/ip/ospf/transmit-delay/configd_update.sh";
				configd:delete "/opt/vyatta/share/tmplscripts/interfaces/openvpn/ip/ospf/transmit-delay/configd_delete.sh";
			}
		}
	}
	augment /if:interfaces/interfaces-tunnel:tunnel/interfaces-tunnel:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/tunnel/ip/ospf/priority/configd_update.sh";
				configd:delete "/opt/vyatta/share/tmplscripts/interfaces/tunnel/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/tunnel/ip/ospf/authentication/plaintext-password/configd_update.sh";
					configd:delete "/opt/vyatta/share/tmplscripts/interfaces/tunnel/ip/ospf/authentication/plaintext-password/configd_delete.sh";
				}
				leaf plaintext {
					type empty;
					configd:help "Enable/disable plain text authentication";
					configd:update "/opt/vyatta/share/tmplscripts/interfaces/tunnel/ip/ospf/authentication/plaintext/configd_update.sh";
					configd:delete "/opt/vyatta/share/tmplscripts/interfaces/tunnel/ip/ospf/authentication/plaintext/configd_delete.sh";
				}
				leaf md5 {
					type empty;
					configd:help "MD5 parameters";
					configd:create "/opt/vyatta/share/tmplscripts/interfaces/tunnel/ip/ospf/authentication/md5/configd_create.sh";
					configd:delete "/opt/vyatta/share/tmplscripts/interfaces/tunnel/ip/ospf/authentication/md5/configd_delete.sh";
				}
				list md5-key-id {
					configd:help "MD5 key id";
					configd:validate "/opt/vyatta/share/tmplscripts/interfaces/tunnel/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/tunnel/ip/ospf/authentication/md5-key-id/md5-key/configd_create.sh";
						configd:update "/opt/vyatta/share/tmplscripts/interfaces/tunnel/ip/ospf/authentication/md5-key-id/md5-key/configd_update.sh";
						configd:delete "/opt/vyatta/share/tmplscripts/interfaces/tunnel/ip/ospf/authentication/md5-key-id/md5-key/configd_delete.sh";
					}
				}
			}
			leaf mtu-ignore {
				type empty;
				configd:help "Disable Maximum Transmission Unit (MTU) mismatch detection";
				configd:create "/opt/vyatta/share/tmplscripts/interfaces/tunnel/ip/ospf/mtu-ignore/configd_create.sh";
				configd:delete "/opt/vyatta/share/tmplscripts/interfaces/tunnel/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/tunnel/ip/ospf/dead-interval/configd_update.sh";
				configd:delete "/opt/vyatta/share/tmplscripts/interfaces/tunnel/ip/ospf/dead-interval/configd_delete.sh";
			}
			leaf hello-interval {
				type uint32 {
					range 1..65535 {
						error-message "Must be between 1-65535";
					}
				}
				configd:help "Interval between hello packets";
				configd:create "/opt/vyatta/share/tmplscripts/interfaces/tunnel/ip/ospf/hello-interval/configd_create.sh";
				configd:delete "/opt/vyatta/share/tmplscripts/interfaces/tunnel/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/tunnel/ip/ospf/retransmit-interval/configd_update.sh";
				configd:delete "/opt/vyatta/share/tmplscripts/interfaces/tunnel/ip/ospf/retransmit-interval/configd_delete.sh";
			}
			leaf cost {
				type uint32 {
					range 1..65535 {
						error-message "Must be between 1-65535";
					}
				}
				configd:help "Interface cost";
				configd:update "/opt/vyatta/share/tmplscripts/interfaces/tunnel/ip/ospf/cost/configd_update.sh";
				configd:delete "/opt/vyatta/share/tmplscripts/interfaces/tunnel/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/tunnel/ip/ospf/network/configd_update.sh";
				configd:delete "/opt/vyatta/share/tmplscripts/interfaces/tunnel/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/tunnel/ip/ospf/transmit-delay/configd_update.sh";
				configd:delete "/opt/vyatta/share/tmplscripts/interfaces/tunnel/ip/ospf/transmit-delay/configd_delete.sh";
			}
		}
	}
	augment /if:interfaces/interfaces-vti:vti/interfaces-vti:ip {
		container ospf {
			presence "true";
			configd:help "Open Shortest Path First (OSPF) parameters";
			leaf priority {
				type uint32 {
					range 0..255 {
						error-message "Must be between 0-255";
					}
				}
				configd:help "Router priority";
				default "1";
				configd:update "/opt/vyatta/share/tmplscripts/interfaces/vti/ip/ospf/priority/configd_update.sh";
				configd:delete "/opt/vyatta/share/tmplscripts/interfaces/vti/ip/ospf/priority/configd_delete.sh";
			}
			container authentication {
				presence "true";
				configd:help "OSPF interface authentication";
				leaf plaintext-password {
					type string {
						pattern "[^\t\n\r ]{1,8}" {
							error-message "Password must be 8 characters or less";
						}
					}
					configd:secret "true";
					configd:help "Plain text password";
					configd:update "/opt/vyatta/share/tmplscripts/interfaces/vti/ip/ospf/authentication/plaintext-password/configd_update.sh";
					configd:delete "/opt/vyatta/share/tmplscripts/interfaces/vti/ip/ospf/authentication/plaintext-password/configd_delete.sh";
				}
				leaf plaintext {
					type empty;
					configd:help "Enable/disable plain text authentication";
					configd:update "/opt/vyatta/share/tmplscripts/interfaces/vti/ip/ospf/authentication/plaintext/configd_update.sh";
					configd:delete "/opt/vyatta/share/tmplscripts/interfaces/vti/ip/ospf/authentication/plaintext/configd_delete.sh";
				}
				leaf md5 {
					type empty;
					configd:help "MD5 parameters";
					configd:create "/opt/vyatta/share/tmplscripts/interfaces/vti/ip/ospf/authentication/md5/configd_create.sh";
					configd:delete "/opt/vyatta/share/tmplscripts/interfaces/vti/ip/ospf/authentication/md5/configd_delete.sh";
				}
				list md5-key-id {
					configd:help "MD5 key id";
					configd:validate "/opt/vyatta/share/tmplscripts/interfaces/vti/ip/ospf/authentication/md5-key-id/configd_validate1.cli";
					key "tagnode";
					leaf tagnode {
						type uint32 {
							range 1..255 {
								error-message "ID must be between (1-255)";
							}
						}
						configd:help "MD5 key id";
					}
					leaf md5-key {
						type string {
							pattern "[^\t\n\r ]{1,16}" {
								error-message "MD5 key must be 16 characters or less";
							}
						}
						configd:help "MD5 key";
						configd:create "/opt/vyatta/share/tmplscripts/interfaces/vti/ip/ospf/authentication/md5-key-id/md5-key/configd_create.sh";
						configd:update "/opt/vyatta/share/tmplscripts/interfaces/vti/ip/ospf/authentication/md5-key-id/md5-key/configd_update.sh";
						configd:delete "/opt/vyatta/share/tmplscripts/interfaces/vti/ip/ospf/authentication/md5-key-id/md5-key/configd_delete.sh";
					}
				}
			}
			leaf mtu-ignore {
				type empty;
				configd:help "Disable Maximum Transmission Unit (MTU) mismatch detection";
				configd:create "/opt/vyatta/share/tmplscripts/interfaces/vti/ip/ospf/mtu-ignore/configd_create.sh";
				configd:delete "/opt/vyatta/share/tmplscripts/interfaces/vti/ip/ospf/mtu-ignore/configd_delete.sh";
			}
			leaf dead-interval {
				type uint32 {
					range 1..65535 {
						error-message "Must be between 1-65535";
					}
				}
				configd:help "Interval after which neighbor is dead";
				default "40";
				configd:update "/opt/vyatta/share/tmplscripts/interfaces/vti/ip/ospf/dead-interval/configd_update.sh";
				configd:delete "/opt/vyatta/share/tmplscripts/interfaces/vti/ip/ospf/dead-interval/configd_delete.sh";
			}
			leaf hello-interval {
				type uint32 {
					range 1..65535 {
						error-message "Must be between 1-65535";
					}
				}
				configd:help "Interval between hello packets";
				configd:create "/opt/vyatta/share/tmplscripts/interfaces/vti/ip/ospf/hello-interval/configd_create.sh";
				configd:delete "/opt/vyatta/share/tmplscripts/interfaces/vti/ip/ospf/hello-interval/configd_delete.sh";
			}
			leaf retransmit-interval {
				type uint32 {
					range 5..65535 {
						error-message "Must be between 5-65535";
					}
				}
				configd:help "Interval between retransmitting lost link state advertisements";
				default "5";
				configd:update "/opt/vyatta/share/tmplscripts/interfaces/vti/ip/ospf/retransmit-interval/configd_update.sh";
				configd:delete "/opt/vyatta/share/tmplscripts/interfaces/vti/ip/ospf/retransmit-interval/configd_delete.sh";
			}
			leaf cost {
				type uint32 {
					range 1..65535 {
						error-message "Must be between 1-65535";
					}
				}
				configd:help "Interface cost";
				configd:update "/opt/vyatta/share/tmplscripts/interfaces/vti/ip/ospf/cost/configd_update.sh";
				configd:delete "/opt/vyatta/share/tmplscripts/interfaces/vti/ip/ospf/cost/configd_delete.sh";
			}
			leaf network {
				type enumeration {
					enum "broadcast" {
						configd:help "Broadcast network type";
					}
					enum "non-broadcast" {
						configd:help "Non-broadcast network type";
					}
					enum "point-to-multipoint" {
						configd:help "Point-to-multipoint network type";
					}
					enum "point-to-point" {
						configd:help "Point-to-point network type";
					}
				}
				configd:help "Network type";
				configd:update "/opt/vyatta/share/tmplscripts/interfaces/vti/ip/ospf/network/configd_update.sh";
				configd:delete "/opt/vyatta/share/tmplscripts/interfaces/vti/ip/ospf/network/configd_delete.sh";
			}
			leaf transmit-delay {
				type uint32 {
					range 1..65535 {
						error-message "Must be between 1-65535";
					}
				}
				configd:help "Link state transmit delay";
				default "1";
				configd:update "/opt/vyatta/share/tmplscripts/interfaces/vti/ip/ospf/transmit-delay/configd_update.sh";
				configd:delete "/opt/vyatta/share/tmplscripts/interfaces/vti/ip/ospf/transmit-delay/configd_delete.sh";
			}
		}
	}
}
