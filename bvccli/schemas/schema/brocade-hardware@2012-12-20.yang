/******************************************************************
* brocade-hardware.yang: Brocade Hardware Management Data Model 
*
* December 2012, Venkat Pogiri
*
* Copyright (c) 2014 by Brocade Communications Systems, Inc.
* All rights reserved.
*******************************************************************/
module brocade-hardware {
    namespace "urn:brocade.com:mgmt:brocade-hardware";
    prefix "hardware";

    /* Linkage Statements */

    import tailf-common {
        prefix tailf;
    }

    import brocade-interface {
        prefix interface; 
    }

    import brocade-common-def {
        prefix common-def;
    }

    import brocade-rbridge {
        prefix rbridge;
    }

    /* Meta Information */

    organization
        "Brocade Communications Systems, Inc.";

    contact
        "Brocade Communications Systems, Inc.
         Postal: 130 Holger Way
                 San Jose, CA 95134
                  U.S.A
         Tel: +1-408-333-8000
         E-mail: support@Brocade.com
         web: www.brocade.com.";

    description
        "This hardware management module is used to manage connectors.
         It can be used to breakout the connectors and set the type
         of the connectors.";

    /* Revision history */

    revision "2012-12-20" {
        description
            "Initial version of this management module.";
    }

    /* Module Definition */

    typedef u-port-type {
        type enumeration {
            enum ethernet {
                value 1;
            }
            enum fibre-channel {
                value 2;
            }
        }
    }

	typedef connector-speed-type {
		type enumeration {
			enum LowMixed {
				value 0;
			}
			enum HighMixed {
				value 1;
			}
			enum FibreChannel {
				value 2;
			}
		}
	}

	typedef connector-group-type {
		type string {
			pattern '((([1-9]|[1-9][0-9]|1[0-9][0-9]|2[0-3][0-9])/)?(([0-9]|[1][0-6]))/([1-9]|[1-9][0-9]|[1-9][0-9][0-9])(:[1-4])?)';
			length "3..16"  {
			}
		}
	}
	
	typedef connector-type {
		type string {
			pattern '((([1-9]|[1-9][0-9]|1[0-9][0-9]|2[0-3][0-9])/)?(([0-9]|[1][0-6]))/([1-9]|[1-9][0-9]|[1-9][0-9][0-9])?)';
			length "3..16"  {
			}
		}

		description
			"The definition for specifying a network interface name in
			a VCS environment. It is in 3-tuple canonical format:
			[rbridge-id]/slot/port.";
	}

	typedef port-type {
		type enumeration {
			enum fibre-channel {
				value 0;
				description "A FirbeChannel Port";
			}
			enum ethernet {
				value 1;
				description "An Ethernet Port";
			}
		}

		description "Definition for specifying the type of port.";
    }

	typedef breakout-type {
		type enumeration {
			enum 40g {
				value 2;
				description "breakout into 40G ports";
            }
        }

        description "Definition for specifying the type of port breakout.";
    }

    typedef tcam-profile-subtype {
        type enumeration {
            enum default {
                value 0;
            }

            enum l2-ipv4-acl {
                value 1;
            }

            enum l2-acl-qos {
                value 2;
            }

            enum ipv4-v6-pbr {
                value 3;
            }

            enum ipv4-v6-qos {
                value 4;
            }

            enum ipv4-v6-mcast {
                value 5;
            }

			enum dyn-arp-insp {
                value 6;
            }

			enum openflow {
                value 7;
            }
        }
    }

    typedef routing-profile-subtype {
        type enumeration {
            enum default {
                value 0;
            }

            enum ipv4-max-route {
                value 1;
            }

            enum ipv4-max-arp {
                value 2;
            }

            enum ipv4-min-v6 {
                value 3;
            }

            enum ipv6-max-route {
                value 4;
            }

            enum ipv6-max-nd {
                value 5;
            }
        }
    }

    typedef vlan-classification-subtype {
        type enumeration {
            enum default {
                value 0;
            }

            enum tor-virtualfabric {
                value 1;
            }

            enum tor-vxlan-gw {
                value 2;
            }

            enum aggregator-basic {
                value 3;
            }

            enum aggregator-virtualfabric {
                value 4;
            }

            enum aggregator-vxlan-gw {
                value 5;
            }
        }
    }

    typedef kap-profile-subtype {
        type enumeration {
            enum default {
                value 0;
            }
        }
    }

	typedef slotnumber {
        type uint32 {
			range 0..16 {
                error-message "Invalid slot number.";
            }
		}
    }

    typedef platform-type {
        type enumeration {
            enum vdx67xx {
                value 1;
            }

            enum vdx69xx {
                value 2;
            }

            enum vdx87xx {
                value 3;
            }
        }
    }

    typedef ecmp-subtype {
        type enumeration {
			enum 8 {
                value 0;
            }
            enum 16 {
                value 1;
            }

            enum 32 {
                value 2;
            }
        }
    }

	typedef openflow-subtype {
        type enumeration {
            enum off {
                value 0;
            }
            enum on {
                value 1;
            }
        }
    }

	typedef lacp-kap-intervaltype {
		type enumeration {
			enum 1000 {
				value 1000;
			}

			enum 30000 {
				value 30000;
			}
		}
	}

    container hardware {
        description 
            "This specifies the group of configuration/operational 
            elements to manage the hardware chracteristics of this
            managed entity."; 
        list connector {
            key "name";

            leaf name {
                type connector-type;
                mandatory true;
            }

			container sfp {
/*
*/

			  	leaf breakout {
					type empty;
				}
/*
				leaf speed1 {
				   	type breakout-type;
				}
*/
			}
		}

        list port-group {
            key "name";

            leaf name {
                type interface:port-group-type;
                mandatory true;
            }

            container mode {
                leaf performance {
                    type empty;
                }
            }
        }

		list connector-group {
			key "id";

			leaf id {
				type connector-group-type;
			}

			leaf speed {
				type connector-speed-type;
            }
        }

		list flexport {
			key id;

			leaf id {
				type interface:interface-type;
				mandatory true;
				description "The port to be changed.";
			}

			container flexport_type {
				leaf type {
					type port-type;
					description "The type to be configured.";
				}

				leaf instance {
					type int32;
					description "The instance to which the port should be configured.";
				}

				leaf skip_deconfig {
					type empty;
					description "Skip plugin notification Errors.";
				}
			}
		}

		container custom-profile {

			list kap-custom-profile {
				key "name";
	
				leaf name {
					type string {
						length 1..64 {
						}
					}
					mandatory true;
				}

				container lacp {

					leaf lacp_hello_interval {
						type lacp-kap-intervaltype;
					}
					leaf lacp_num_entry {
						type uint32 {
							range "0 .. 769" {
                           	}
                        }
                    }
                }

				container xstp {

                    leaf xstp_hello_interval {
                        type uint32 {
                            range "1000 .. 6000" {
                            }
                        }
                    }
                    leaf xstp_num_entry {
                        type uint32 {
                           	range "0 .. 769" {
                           }
                        }
                    }
                }

				container rpvst {

                    leaf rpvst_hello_interval {
                        type uint32 {
                            range "1000 .. 6000" {
                            }
                        }
                    }
                    leaf rpvst_num_entry {
                        type uint32 {
							range "0 .. 512" {
							}
						}
                    }
                }

                container udld {

                   	leaf udld_hello_interval {
                       	type uint32 {
                           range "100 .. 6000" {
                           }
                       }
                   }

                   leaf udld_num_entry {
                       	type uint32 {
							range "0 .. 769" {
							}
						}
					}
				}

                container bfd-vxlan {

                    leaf bfd_vxlan_hello_interval {
                        type uint32 {
                            range "50 .. 1000" {
                            }
                        }
                    }
                    leaf bfd_vxlan_num_entry {
                        type uint32 {
                            range "0 .. 30" {
                            }
                        }
                    }
                }

				container bfd-l3 {

                    leaf bfd_l3_hello_interval {
                        type uint32 {
                            range "50 .. 1000" {
                            }
                        }
                    }
                    leaf bfd_l3_num_entry {
                        type uint32 {
                            range "0 .. 800" {
                            }
                        }
                    }
                }

                container fcoe {

                    leaf fcoe_hello_interval {
                        type uint32 {
                            range "1 .. 6" {
                            }
                        }
                    }
                    leaf fcoe_num_entry {
                        type uint32 {
                            range "0 .. 769" {
                            }
                        }
                    }
                }
			}
		}
	}

	grouping profile-cmds {
		container hardware-profile {

			container tcam {

				container predefined {
 
					leaf tcam_profiletype {
						type tcam-profile-subtype;
					}
				}
			}

			container route-table {

				container predefined {

					leaf routing_profiletype {
						type routing-profile-subtype;
					}

					container routing_parameter {

						leaf maximum_paths {
							type ecmp-subtype;
						}

						leaf openflow_enable {
							type openflow-subtype;
						}
					}	
				}
			}

			container vlan-classification {

				container predefined {

					leaf vlan_profiletype {
						type vlan-classification-subtype;
					}
				}
			}

			container kap {

				container predefined {

                    leaf kap_profiletype {
						type kap-profile-subtype;
                    }
				}

				container customized {
	
					leaf kap_profilename {
						type string {
                   			length 1..64 {
							}
						}
                    }
                }
			}

/*	slot based profile is currently disabled
			list slot {

                key "slotid";

                leaf slotid {
					type slotnumber; 
                }

   			 	container kap {

                	container predefined {

                    	leaf kap_profiletype {
                        	type kap-profile-subtype;
                    	}
                	}

                	container customized {

                    	leaf kap_profilename {
                        	type common-def:name-string128;
                    	}
					}
                }
            }
*/
		}
	}

	augment "/rbridge:rbridge-id" {
		uses profile-cmds;
	}

	augment "/common-def:show" {
		container hardware {
			tailf:action connector-group {
				input {}
				output {}
			}
		}

		container hardware-profile {

			tailf:action hardware-profile {

			input {
				choice profile-type {
				case tcam {
					leaf tcam {
					    type tcam-profile-subtype;
						mandatory true;
					}
				}	

				case route-table {
					container routing {
	
						leaf route-table {
							type routing-profile-subtype;
							mandatory true;
						}

						leaf openflow-flag {
							type empty;
							mandatory false;
						}
					}
				}

				case vlan {
					leaf vlan {
						type vlan-classification-subtype;
						mandatory true;
					}
				}

				case kap {
					leaf kap {
                        type kap-profile-subtype;
                        mandatory true;
                    }
                }

				case current {
					leaf current {
						type empty;
						mandatory true;
					} 
				}
				}

				leaf rbridge-id {
					type common-def:rbridge-id-all-type;
					mandatory false;
				}
			}
			output {}
			}
		}
	}

	rpc get-flexports {
		output {
			list flexport-list {
				leaf port-id {
					type string;
                }
            }
       }
    }
}
