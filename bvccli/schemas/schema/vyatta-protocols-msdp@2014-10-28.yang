module vyatta-protocols-msdp {
	namespace "urn:vyatta.com:mgmt:vyatta-protocols-msdp";
	prefix protocols-msdp;

	import vyatta-types {
		prefix types;
	}
	import vyatta-protocols {
		prefix protocols;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /protocols:protocols {
		container msdp {
			presence "true";
			configd:priority "790";
			configd:help "Multicast Source Discovery Protocol (MSDP)";
			configd:validate "/opt/vyatta/share/tmplscripts/protocols/msdp/configd_validate1.cli";
			list peer {
				configd:priority "795";
				configd:help "Configure an MSDP peer";
				configd:create "/opt/vyatta/share/tmplscripts/protocols/msdp/peer/configd_create.sh";
				configd:delete "/opt/vyatta/share/tmplscripts/protocols/msdp/peer/configd_delete.sh";
				key "tagnode";
				leaf tagnode {
					type types:ipv4-address;
					configd:help "Configure an MSDP peer";
				}
				container export {
					presence "true";
					configd:help "Configure which outgoing filter for (S,G) entries are advertising to the MSDP peer";
					configd:delete "/opt/vyatta/share/tmplscripts/protocols/msdp/peer/export/configd_delete.sh";
					configd:validate "/opt/vyatta/share/tmplscripts/protocols/msdp/peer/export/configd_validate1.cli";
					leaf access-list {
						type uint32 {
							configd:syntax "/opt/vyatta/share/tmplscripts/protocols/msdp/peer/export/access-list/configd_syntax1.cli";
						}
						configd:help "Configure which outgoing filter for (S,G) entries are advertising to the MSDP peer";
						configd:allowed "/opt/vyatta/share/tmplscripts/protocols/msdp/peer/export/access-list/configd_allowed.sh";
						configd:delete "/opt/vyatta/share/tmplscripts/protocols/msdp/peer/export/access-list/configd_delete.sh";
						configd:update "/opt/vyatta/share/tmplscripts/protocols/msdp/peer/export/access-list/configd_update.sh";
						configd:validate "/opt/vyatta/share/tmplscripts/protocols/msdp/peer/export/access-list/configd_validate1.cli";
					}
					leaf rp-list {
						type string {
							configd:syntax "/opt/vyatta/share/tmplscripts/protocols/msdp/peer/export/rp-list/configd_syntax1.cli";
						}
						configd:help "Configure which outgoing filter for (S,G) entries are advertising to the MSDP peer";
						configd:allowed "/opt/vyatta/share/tmplscripts/protocols/msdp/peer/export/rp-list/configd_allowed.sh";
						configd:delete "/opt/vyatta/share/tmplscripts/protocols/msdp/peer/export/rp-list/configd_delete.sh";
						configd:update "/opt/vyatta/share/tmplscripts/protocols/msdp/peer/export/rp-list/configd_update.sh";
						configd:validate "/opt/vyatta/share/tmplscripts/protocols/msdp/peer/export/rp-list/configd_validate1.cli";
					}
				}
				container default-peer {
					presence "true";
					configd:help "Configure an MSDP default peer";
					configd:delete "/opt/vyatta/share/tmplscripts/protocols/msdp/peer/default-peer/configd_delete.sh";
					configd:validate "/opt/vyatta/share/tmplscripts/protocols/msdp/peer/default-peer/configd_validate1.cli";
					leaf priority {
						type uint32;
						configd:help "Configure priority for default peer";
						configd:update "/opt/vyatta/share/tmplscripts/protocols/msdp/peer/default-peer/priority/configd_update.sh";
					}
					leaf prefix-list {
						type string {
							configd:syntax "/opt/vyatta/share/tmplscripts/protocols/msdp/peer/default-peer/prefix-list/configd_syntax1.cli";
						}
						configd:help "Prefix-list that specifies the peer will be a default peer only for the listed prefixes";
						configd:allowed "/opt/vyatta/share/tmplscripts/protocols/msdp/peer/default-peer/prefix-list/configd_allowed.sh";
						configd:delete "/opt/vyatta/share/tmplscripts/protocols/msdp/peer/default-peer/prefix-list/configd_delete.sh";
						configd:update "/opt/vyatta/share/tmplscripts/protocols/msdp/peer/default-peer/prefix-list/configd_update.sh";
						configd:validate "/opt/vyatta/share/tmplscripts/protocols/msdp/peer/default-peer/prefix-list/configd_validate1.cli";
					}
				}
				leaf holdtime {
					type uint32 {
						range 3..75 {
							error-message "Must be between 3-75 sec";
						}
					}
					configd:help "Configure hold time during which keepalive messages are waited before declaring the MSDP peer down";
					configd:update "/opt/vyatta/share/tmplscripts/protocols/msdp/peer/holdtime/configd_update.sh";
					configd:delete "/opt/vyatta/share/tmplscripts/protocols/msdp/peer/holdtime/configd_delete.sh";
				}
				leaf password {
					type string;
					configd:secret "true";
					configd:help "Password for the given peer";
					configd:update "/opt/vyatta/share/tmplscripts/protocols/msdp/peer/password/configd_update.sh";
					configd:delete "/opt/vyatta/share/tmplscripts/protocols/msdp/peer/password/configd_delete.sh";
				}
				leaf data-encapsulation-ttl {
					type uint32 {
						range 1..255 {
							error-message "Must be between 1-255";
						}
					}
					configd:help "To limit which multicast data packets are sent in SA messages to a MSDP peer";
					configd:create "/opt/vyatta/share/tmplscripts/protocols/msdp/peer/data-encapsulation-ttl/configd_create.sh";
					configd:delete "/opt/vyatta/share/tmplscripts/protocols/msdp/peer/data-encapsulation-ttl/configd_delete.sh";
				}
				leaf connect-retry {
					type uint32 {
						range 1..60 {
							error-message "Must be between 1-60 sec";
						}
					}
					configd:help "Configure connect-retry time period after which the closed TCP session is tried to restore";
					configd:update "/opt/vyatta/share/tmplscripts/protocols/msdp/peer/connect-retry/configd_update.sh";
					configd:delete "/opt/vyatta/share/tmplscripts/protocols/msdp/peer/connect-retry/configd_delete.sh";
				}
				leaf shutdown {
					type empty;
					configd:help "To administratively shut down a configured MSDP peer";
					configd:allowed "/opt/vyatta/share/tmplscripts/protocols/msdp/peer/shutdown/configd_allowed.sh";
					configd:create "/opt/vyatta/share/tmplscripts/protocols/msdp/peer/shutdown/configd_create.sh";
					configd:delete "/opt/vyatta/share/tmplscripts/protocols/msdp/peer/shutdown/configd_delete.sh";
				}
				leaf keepalive {
					type uint32 {
						range 1..60 {
							error-message "Must be between 1-60 sec";
						}
					}
					configd:help "Configure keep alive time period at which the messages will be send to a MSDP peer";
					configd:update "/opt/vyatta/share/tmplscripts/protocols/msdp/peer/keepalive/configd_update.sh";
					configd:delete "/opt/vyatta/share/tmplscripts/protocols/msdp/peer/keepalive/configd_delete.sh";
				}
				leaf local-address {
					type types:ipv4-address;
					configd:help "IPv4 address is used as the source IP for setting up a TCP connection to the peer";
					configd:delete "/opt/vyatta/share/tmplscripts/protocols/msdp/peer/local-address/configd_delete.sh";
					configd:update "/opt/vyatta/share/tmplscripts/protocols/msdp/peer/local-address/configd_update.sh";
				}
				container import {
					presence "true";
					configd:help "Configure which incomming filter for (S,G) entries received from the MSDP peer";
					configd:delete "/opt/vyatta/share/tmplscripts/protocols/msdp/peer/import/configd_delete.sh";
					configd:validate "/opt/vyatta/share/tmplscripts/protocols/msdp/peer/import/configd_validate1.cli";
					leaf access-list {
						type uint32 {
							configd:syntax "/opt/vyatta/share/tmplscripts/protocols/msdp/peer/import/access-list/configd_syntax1.cli";
						}
						configd:help "Configure which incomming filter for (S,G) entries received from the MSDP peer";
						configd:allowed "/opt/vyatta/share/tmplscripts/protocols/msdp/peer/import/access-list/configd_allowed.sh";
						configd:delete "/opt/vyatta/share/tmplscripts/protocols/msdp/peer/import/access-list/configd_delete.sh";
						configd:update "/opt/vyatta/share/tmplscripts/protocols/msdp/peer/import/access-list/configd_update.sh";
						configd:validate "/opt/vyatta/share/tmplscripts/protocols/msdp/peer/import/access-list/configd_validate1.cli";
					}
					leaf rp-list {
						type string {
							configd:syntax "/opt/vyatta/share/tmplscripts/protocols/msdp/peer/import/rp-list/configd_syntax1.cli";
						}
						configd:help "Configure which incomming filter for (S,G) entries received from the MSDP peer";
						configd:allowed "/opt/vyatta/share/tmplscripts/protocols/msdp/peer/import/rp-list/configd_allowed.sh";
						configd:delete "/opt/vyatta/share/tmplscripts/protocols/msdp/peer/import/rp-list/configd_delete.sh";
						configd:update "/opt/vyatta/share/tmplscripts/protocols/msdp/peer/import/rp-list/configd_update.sh";
						configd:validate "/opt/vyatta/share/tmplscripts/protocols/msdp/peer/import/rp-list/configd_validate1.cli";
					}
				}
			}
			container export {
				presence "true";
				configd:priority "793";
				configd:help "Configure which (S,G) entries are advertising in SA messages to other peers";
				configd:delete "/opt/vyatta/share/tmplscripts/protocols/msdp/export/configd_delete.sh";
				configd:validate "/opt/vyatta/share/tmplscripts/protocols/msdp/export/configd_validate1.cli";
				leaf access-list {
					type uint32 {
						configd:syntax "/opt/vyatta/share/tmplscripts/protocols/msdp/export/access-list/configd_syntax1.cli";
					}
					configd:help "Configure which (S,G) entries are advertising in SA messages to other peers";
					configd:allowed "/opt/vyatta/share/tmplscripts/protocols/msdp/export/access-list/configd_allowed.sh";
					configd:delete "/opt/vyatta/share/tmplscripts/protocols/msdp/export/access-list/configd_delete.sh";
					configd:update "/opt/vyatta/share/tmplscripts/protocols/msdp/export/access-list/configd_update.sh";
					configd:validate "/opt/vyatta/share/tmplscripts/protocols/msdp/export/access-list/configd_validate1.cli";
				}
				leaf rp-list {
					type string {
						configd:syntax "/opt/vyatta/share/tmplscripts/protocols/msdp/export/rp-list/configd_syntax1.cli";
					}
					configd:help "Configure which (S,G) entries are advertising in SA messages to other peers";
					configd:allowed "/opt/vyatta/share/tmplscripts/protocols/msdp/export/rp-list/configd_allowed.sh";
					configd:delete "/opt/vyatta/share/tmplscripts/protocols/msdp/export/rp-list/configd_delete.sh";
					configd:update "/opt/vyatta/share/tmplscripts/protocols/msdp/export/rp-list/configd_update.sh";
					configd:validate "/opt/vyatta/share/tmplscripts/protocols/msdp/export/rp-list/configd_validate1.cli";
				}
			}
			list peer-group {
				configd:priority "796";
				configd:help "Configure an MSDP peer-group (peers common paramters)";
				configd:create "/opt/vyatta/share/tmplscripts/protocols/msdp/peer-group/configd_create.sh";
				configd:delete "/opt/vyatta/share/tmplscripts/protocols/msdp/peer-group/configd_delete.sh";
				key "tagnode";
				leaf tagnode {
					type string;
					configd:help "Configure an MSDP peer-group (peers common paramters)";
				}
				leaf-list peer {
					type types:ipv4-address;
					ordered-by "user";
					configd:priority "797";
					configd:help "IP address of the MSDP peer to be a member of the peer-group";
					configd:allowed "/opt/vyatta/share/tmplscripts/protocols/msdp/peer-group/peer/configd_allowed.sh";
					configd:create "/opt/vyatta/share/tmplscripts/protocols/msdp/peer-group/peer/configd_create.sh";
					configd:delete "/opt/vyatta/share/tmplscripts/protocols/msdp/peer-group/peer/configd_delete.sh";
					configd:validate "/opt/vyatta/share/tmplscripts/protocols/msdp/peer-group/peer/configd_validate1.cli";
				}
				container export {
					presence "true";
					configd:help "Configure which (S,G) entries are advertising in SA messages to peer-group members";
					configd:delete "/opt/vyatta/share/tmplscripts/protocols/msdp/peer-group/export/configd_delete.sh";
					configd:validate "/opt/vyatta/share/tmplscripts/protocols/msdp/peer-group/export/configd_validate1.cli";
					leaf access-list {
						type uint32 {
							configd:syntax "/opt/vyatta/share/tmplscripts/protocols/msdp/peer-group/export/access-list/configd_syntax1.cli";
						}
						configd:help "Prefix-list that controls which local sources are advertised by peer (applied to members of the peer-group)";
						configd:allowed "/opt/vyatta/share/tmplscripts/protocols/msdp/peer-group/export/access-list/configd_allowed.sh";
						configd:delete "/opt/vyatta/share/tmplscripts/protocols/msdp/peer-group/export/access-list/configd_delete.sh";
						configd:update "/opt/vyatta/share/tmplscripts/protocols/msdp/peer-group/export/access-list/configd_update.sh";
						configd:validate "/opt/vyatta/share/tmplscripts/protocols/msdp/peer-group/export/access-list/configd_validate1.cli";
					}
					leaf rp-list {
						type string {
							configd:syntax "/opt/vyatta/share/tmplscripts/protocols/msdp/peer-group/export/rp-list/configd_syntax1.cli";
						}
						configd:help "Prefix-list that controls which rendezvous points are advertised by peer (applied to members of the peer-group)";
						configd:allowed "/opt/vyatta/share/tmplscripts/protocols/msdp/peer-group/export/rp-list/configd_allowed.sh";
						configd:delete "/opt/vyatta/share/tmplscripts/protocols/msdp/peer-group/export/rp-list/configd_delete.sh";
						configd:update "/opt/vyatta/share/tmplscripts/protocols/msdp/peer-group/export/rp-list/configd_update.sh";
						configd:validate "/opt/vyatta/share/tmplscripts/protocols/msdp/peer-group/export/rp-list/configd_validate1.cli";
					}
				}
				leaf holdtime {
					type uint32 {
						range 3..75 {
							error-message "Must be between 3-75 sec";
						}
					}
					configd:help "Configure hold time during which keepalive messages are waited before declaring the MSDP peer down";
					configd:update "/opt/vyatta/share/tmplscripts/protocols/msdp/peer-group/holdtime/configd_update.sh";
					configd:delete "/opt/vyatta/share/tmplscripts/protocols/msdp/peer-group/holdtime/configd_delete.sh";
				}
				leaf data-encapsulation-ttl {
					type uint32 {
						range 1..255 {
							error-message "Must be between 1-255";
						}
					}
					configd:help "To limit which multicast data packets are sent in SA messages to a MSDP peer";
					configd:create "/opt/vyatta/share/tmplscripts/protocols/msdp/peer-group/data-encapsulation-ttl/configd_create.sh";
					configd:delete "/opt/vyatta/share/tmplscripts/protocols/msdp/peer-group/data-encapsulation-ttl/configd_delete.sh";
				}
				leaf connect-retry {
					type uint32 {
						range 1..60 {
							error-message "Must be between 1-60 sec";
						}
					}
					configd:help "Configure connect-retry time period after which the closed TCP session is tried to restore";
					configd:update "/opt/vyatta/share/tmplscripts/protocols/msdp/peer-group/connect-retry/configd_update.sh";
					configd:delete "/opt/vyatta/share/tmplscripts/protocols/msdp/peer-group/connect-retry/configd_delete.sh";
				}
				leaf shutdown {
					type empty;
					configd:priority "799";
					configd:help "To administratively shut down a configured MSDP peer";
					configd:allowed "/opt/vyatta/share/tmplscripts/protocols/msdp/peer-group/shutdown/configd_allowed.sh";
					configd:create "/opt/vyatta/share/tmplscripts/protocols/msdp/peer-group/shutdown/configd_create.sh";
					configd:delete "/opt/vyatta/share/tmplscripts/protocols/msdp/peer-group/shutdown/configd_delete.sh";
				}
				leaf keepalive {
					type uint32 {
						range 1..60 {
							error-message "Must be between 1-60 sec";
						}
					}
					configd:help "Configure keep alive time period at which the messages will be send to a MSDP peer";
					configd:update "/opt/vyatta/share/tmplscripts/protocols/msdp/peer-group/keepalive/configd_update.sh";
					configd:delete "/opt/vyatta/share/tmplscripts/protocols/msdp/peer-group/keepalive/configd_delete.sh";
				}
				container import {
					presence "true";
					configd:help "Configure which incomming filter for (S,G) entries received from the MSDP peer-group";
					configd:delete "/opt/vyatta/share/tmplscripts/protocols/msdp/peer-group/import/configd_delete.sh";
					configd:validate "/opt/vyatta/share/tmplscripts/protocols/msdp/peer-group/import/configd_validate1.cli";
					leaf access-list {
						type uint32 {
							configd:syntax "/opt/vyatta/share/tmplscripts/protocols/msdp/peer-group/import/access-list/configd_syntax1.cli";
						}
						configd:help "Prefix-list that controls which local sources are received from the other peer (applied to members of the peer-group)";
						configd:allowed "/opt/vyatta/share/tmplscripts/protocols/msdp/peer-group/import/access-list/configd_allowed.sh";
						configd:delete "/opt/vyatta/share/tmplscripts/protocols/msdp/peer-group/import/access-list/configd_delete.sh";
						configd:update "/opt/vyatta/share/tmplscripts/protocols/msdp/peer-group/import/access-list/configd_update.sh";
						configd:validate "/opt/vyatta/share/tmplscripts/protocols/msdp/peer-group/import/access-list/configd_validate1.cli";
					}
					leaf rp-list {
						type string {
							configd:syntax "/opt/vyatta/share/tmplscripts/protocols/msdp/peer-group/import/rp-list/configd_syntax1.cli";
						}
						configd:help "Prefix-list that controls which rendezvous points are received from the other peer (applied to members of the peer-group)";
						configd:allowed "/opt/vyatta/share/tmplscripts/protocols/msdp/peer-group/import/rp-list/configd_allowed.sh";
						configd:delete "/opt/vyatta/share/tmplscripts/protocols/msdp/peer-group/import/rp-list/configd_delete.sh";
						configd:update "/opt/vyatta/share/tmplscripts/protocols/msdp/peer-group/import/rp-list/configd_update.sh";
						configd:validate "/opt/vyatta/share/tmplscripts/protocols/msdp/peer-group/import/rp-list/configd_validate1.cli";
					}
				}
			}
			list mesh-group {
				configd:priority "797";
				configd:help "Configure a Multicast Source Discovery Protocol (MSDP) peer to be a member of a mesh group";
				configd:validate "/opt/vyatta/share/tmplscripts/protocols/msdp/mesh-group/configd_validate1.cli";
				key "tagnode";
				leaf tagnode {
					type string;
					configd:help "Configure a Multicast Source Discovery Protocol (MSDP) peer to be a member of a mesh group";
				}
				leaf-list peer {
					type types:ipv4-address;
					ordered-by "user";
					configd:help "IP address of the MSDP peer to be a member of the mesh group";
					configd:allowed "/opt/vyatta/share/tmplscripts/protocols/msdp/mesh-group/peer/configd_allowed.sh";
					configd:create "/opt/vyatta/share/tmplscripts/protocols/msdp/mesh-group/peer/configd_create.sh";
					configd:delete "/opt/vyatta/share/tmplscripts/protocols/msdp/mesh-group/peer/configd_delete.sh";
					configd:validate "/opt/vyatta/share/tmplscripts/protocols/msdp/mesh-group/peer/configd_validate1.cli";
				}
			}
			container import {
				presence "true";
				configd:priority "793";
				configd:help "Configure which (S,G) entries receiving in SA messages frome other peers are cached";
				configd:delete "/opt/vyatta/share/tmplscripts/protocols/msdp/import/configd_delete.sh";
				configd:validate "/opt/vyatta/share/tmplscripts/protocols/msdp/import/configd_validate1.cli";
				leaf access-list {
					type uint32 {
						configd:syntax "/opt/vyatta/share/tmplscripts/protocols/msdp/import/access-list/configd_syntax1.cli";
					}
					configd:help "Configure which (S,G) entries receiving in SA messages frome other peers are cached by the given access-list";
					configd:allowed "/opt/vyatta/share/tmplscripts/protocols/msdp/import/access-list/configd_allowed.sh";
					configd:delete "/opt/vyatta/share/tmplscripts/protocols/msdp/import/access-list/configd_delete.sh";
					configd:update "/opt/vyatta/share/tmplscripts/protocols/msdp/import/access-list/configd_update.sh";
					configd:validate "/opt/vyatta/share/tmplscripts/protocols/msdp/import/access-list/configd_validate1.cli";
				}
				leaf rp-list {
					type string {
						configd:syntax "/opt/vyatta/share/tmplscripts/protocols/msdp/import/rp-list/configd_syntax1.cli";
					}
					configd:help "Configure which (S,G) entries receiving in SA messages frome other peers are cached";
					configd:allowed "/opt/vyatta/share/tmplscripts/protocols/msdp/import/rp-list/configd_allowed.sh";
					configd:delete "/opt/vyatta/share/tmplscripts/protocols/msdp/import/rp-list/configd_delete.sh";
					configd:update "/opt/vyatta/share/tmplscripts/protocols/msdp/import/rp-list/configd_update.sh";
					configd:validate "/opt/vyatta/share/tmplscripts/protocols/msdp/import/rp-list/configd_validate1.cli";
				}
			}
			leaf originated-id {
				type types:ipv4-address;
				configd:priority "793";
				configd:help "Allow a MSDP speaker that originates a SA message to use the IP address as the rendezvous point (RP) address in the SA message";
				configd:update "/opt/vyatta/share/tmplscripts/protocols/msdp/originated-id/configd_update.sh";
				configd:delete "/opt/vyatta/share/tmplscripts/protocols/msdp/originated-id/configd_delete.sh";
			}
		}
	}
}
