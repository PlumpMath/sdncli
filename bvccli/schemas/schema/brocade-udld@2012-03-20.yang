/***********************************************************************
 * brocade-udld.yang : Brocade UDLD module.
 * 
 * March 2012, Sachin Holla
 *
 * Copyright (c) 2011 by Brocade Communications Systems, Inc.
 * All rights reserved.
 *
 **********************************************************************/

module brocade-udld {
    namespace "urn:brocade.com:mgmt:brocade-udld";
    prefix "udld";

    import tailf-common      { prefix "tailf";  }
    import brocade-interface { prefix "intf";   }

    organization
        "Brocade Communications Systems, Inc.";

    contact
        "Brocade Communications Systems, Inc.
         Postal: 130 Holger Way
                 San Jose, CA 95134
                 U.S.A
         Tel: +1-408-333-8000
         E-mail: support@Brocade.com
         Web: www.brocade.com
         ";

    description
        "This management module is an instrumentation to manage UDLD
         protocol configuration.

         Glossary of the terms used:
         ---------------------------
         PDU    - Protocol Data Unit. In the context of this module PDU
                  refers to Layer2 frame transmitted or received by
                  UDLD protocol.
         UDLD   - UniDirectional Link Detection
         ";

    revision "2012-03-20" {
        description
            "Initial version; defines UDLD protocol configurations and
             interface configuration to enable and disable UDLD on it.";
    }


    augment "/intf:protocol" {
        container udld {
            presence true;
            description
                "UDLD protocol configuration. UDLD protocol will be
                 enabled when '/protocol/udld' container is created. To
                 disable delete it or set '/protocol/udld/shutdown'
                 leaf";

            leaf hello {
                description
                    "Hello interval is the time period between
                     successive PDU transmissions. UDLD protocol also
                     expects to receive PDUs from the peer at the same
                     rate.
                     Hello interval is measured in deciseconds (100 
                     milliseconds). Default hello interval is 5.
                     ";
                type uint32 {
                    range "1..60";
                }
                default 5;
                units "100 milliseconds";
            }

            leaf multiplier {
                description
                    "Multiplier configures UDLD protocol timeout, which
                     is the product of multiplier and hello interval. If
                     no UDLD PDU is received over a link during timeout
                     period, the link is deemed unidirectional.
                     Default multiplier value is 5.
                     ";
                type uint32 {
                    range "3..10";
                }
                default 5;
            }

            leaf shutdown {
                description
                    "When present indicates that UDLD protocol is
                     disabled on this switch. Disabling UDLD protocol
                     will not clear other configurations.";
                type empty;
            }
        }
    }

    grouping udld-intf-configs {
        container udld {
            description
                "Interface specific UDLD configurations.";

            leaf udld-enable {
                description
                    "When present, indicates that UDLD protocol is
                     activated on this interface. By default the UDLD
                     will not be active on any interface. It needs to
                     be enabled explicitly.";
                type empty;
            }
        }
    }


    augment "/intf:interface/intf:gigabitethernet" {
        uses udld-intf-configs;
    }

    augment "/intf:interface/intf:tengigabitethernet" {
        uses udld-intf-configs;
    }

    augment "/intf:interface/intf:fortygigabitethernet" {
        uses udld-intf-configs;
    }

    augment "/intf:interface/intf:hundredgigabitethernet" {
        uses udld-intf-configs;
    }

}
