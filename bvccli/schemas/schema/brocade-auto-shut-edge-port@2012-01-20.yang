/******************************************************************
* Logical Chassis CLI Yang model that will contain logical chassis clis
*
*   June 2014-2015, Anand Subramanian
*
* Copyright (c) 2014 by Brocade Communications Systems, Inc.
* All rights reserved.
*******************************************************************/

module brocade-auto-shut-edge-port {
    namespace "http://brocade.com/ns/brocade-auto-shut-edge-port";
    prefix brocade-auto-shut-edge-port;

    import tailf-common    { 
        prefix "tailf";  
    }

    //import brocade-vcs {
      //  prefix brocade-vcs;
    //}

    import brocade-rbridge {
        prefix rbridge;
    }

	organization
	"Brocade Communications Inc.";

	contact
	"Brocade Communications Systems, Inc.
	Postal: 130 Holger Way
	San Jose, CA 95134             
	U.S.A
	Tel: +1-408-333-6061
	E-mail: support@Brocade.com
	web: www.brocade.com.";

	description
	"This module provides interface to provision auto-shut on edge ports";

    revision "2012-01-20" {
        description
            "Initial version of this management module.";
    }

    grouping auto-shut-edge-port-cmds {
        container vcs {
            
            container auto-shut {
                //tailf:display-when '((/vcsmode/vcs-mode = "true") and (/vcsmode/vcs-cluster-mode = "true"))';
                //tailf:cli-incomplete-command;

                leaf lag {
                    type empty;
                }
            }
        }
    }

    augment "/rbridge:rbridge-id" {
        uses auto-shut-edge-port-cmds;
    }
}
