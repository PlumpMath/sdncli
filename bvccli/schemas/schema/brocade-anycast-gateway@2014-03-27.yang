/***********************************************************************
 * brocade-anycast-gateway.yang: Brocade anycast-gateway data model
 *
 * March 2014, Sachin Rastogi
 * Copyright (c) 2011 by Brocade Communications Systems, Inc.
 * All rights reserved.
 *
 **********************************************************************/
module brocade-anycast-gateway {
	namespace "urn:brocade.com:mgmt:brocade-anycast-gateway";
	prefix "anycast-gateway";

   	import brocade-rbridge {
        prefix rbridge;
    }

    import brocade-interface {
        prefix interface;
    }

    import tailf-common {
        prefix tailf;
    }

    import ietf-inet-types {
        prefix inet;
    }

    import brocade-mac-access-list {
        prefix mac-access-list;
    }

    import brocade-vrrp {
        prefix vrrp;
    }

	import brocade-ip-config {
        prefix ip-config;
    }

	import brocade-ipv6-config {
        prefix ipv6-config;
    }

	import brocade-common-def {
        prefix "comn";
    }

    import brocade-vcs {
        prefix vcs;
    }

    organization
        "Brocade Communications Systems, Inc.";

    contact
        "Brocade Communications Systems, Inc.
         Postal: 1745 Technology Drive,
                 San Jose, CA 95110
                  U.S.A
         Tel: +1-408-392-6061
         E-mail: support@Brocade.com
         web: www.brocade.com.";

    description
         "This module describes the data model for anycast gateway";

    revision "2014-03-27" {
        description
            "Initial version of this management module.";
    }

    typedef gateway-id-type {
        type uint32 {
            range "1..255" {
            }
        }
    }

    grouping anycast-gateway-common {
        	container gratuitous-arp {

            	leaf gve-timer {
                	type uint32 {
                    	range "0..360" {
                    	}
                	}
                	default 0;
            	}
        	}

			leaf hold-time {
				type uint32 {
					range "1..360" {
					}
				}
			}

			leaf load-balancing-disable {
				type empty;
			}

			leaf enable {
				type empty;
			}

			leaf description {
				//tailf:sort-priority 85;
				type string {
					length "1 .. 63";
				}
			}
    }

	augment /interface:interface-vlan/interface:interface/interface:ve {
        when "((/vcs:vcsmode/vcs:vcs-mode = 'true') and 
            (/vcs:vcsmode/vcs:vcs-cluster-mode = 'true'))" {
        }

			container attach {

            	container rbridge-id {

                	leaf rb-add {
                    	type comn:ui32-range {
                        }
                	}
                	leaf rb-remove {
                    	type comn:ui32-range {
                        }
                	}
            	}
			}
	}

	augment /interface:interface-vlan/interface:interface/interface:ve/interface:ip {
        when "((/vcs:vcsmode/vcs:vcs-mode = 'true') and 
            (/vcs:vcsmode/vcs:vcs-cluster-mode = 'true'))" {
        }

		list ip-anycast-gateway {
			key ip-gw-id;

            leaf ip-gw-id {
                type uint32 {
                    range "1..255" {
                    }
                }
            }

			leaf ipv4-gateway-address {
				type comn:ipv4-prefix-mask;
			}

			uses anycast-gateway-common;
		}
	}

	augment /interface:interface-vlan/interface:interface/interface:ve/interface:ipv6 {
        when "((/vcs:vcsmode/vcs:vcs-mode = 'true') and 
            (/vcs:vcsmode/vcs:vcs-cluster-mode = 'true'))" {
        }
		list ipv6-anycast-gateway {
			key ipv6-gw-id;

            leaf ipv6-gw-id {
                type uint32 {
                    range "1..255" {
                    }
                }
            }

			list ipv6-gateway-address {
				key ipv6-gw-addr;

				leaf ipv6-gw-addr {
					type comn:ipv6-address-prefix;
					description "Anycast gateway IPv6 address";
				}
			}

			uses anycast-gateway-common;
		}
	}

    grouping anycast-gateway-local-common {
        leaf enable_local {
            type empty;
        }

        leaf disable_local {
            type empty;
        }

        container load-balancing {

            leaf basic {
                type empty;
            }

            leaf threshold-priority {
                type uint32 {
                    range "1..254" {
                    }
                }
                description "Threshold Priority";
            }
        }

        /*leaf install-default-route {
            type empty;
        }*/
    }

	augment /rbridge:rbridge-id/interface:interface/interface:ve/ip-config:ip {
        when "((/vcs:vcsmode/vcs:vcs-mode = 'true') and 
                (/vcs:vcsmode/vcs:vcs-cluster-mode = 'true'))" {
        }

            list ip-local-anycast-gateway {
                key local-ip-gw-id;

				leaf local-ip-gw-id {
					type uint32 {
              			range "1..255" {
                		}
            		}
        		}

                uses anycast-gateway-local-common;

        		container track {

					list interface {
						key "interface-type interface-name";

						leaf interface-type {
							type vrrp:track-iftype;
						}

						leaf interface-name {
							type vrrp:track-ifname;
						}

						leaf interface-priority {
							type uint32 {
								range "1..254" {
								}
							}
							mandatory true;
							description "Track Priority";
						}
					}

            		list network {
                		key "network-address";

                		leaf network-address {
							type comn:ipv4-prefix-mask;
                		}

                		leaf network-priority {
                    		type uint32 {
                        		range "1..254" {
                        		}
                    		}
							mandatory true;
                    		description "Track Priority";
                		}
            		}

            		list next-hop {
                		key "next-hop-address";

                		leaf next-hop-address {
                    		type inet:ip-address;
                		}

                		leaf next-hop-priority {
                    		type uint32 {
                        		range "1..254" {
                        		}
                    		}
							mandatory true;
                    		description "Track Priority";
                		}
            		}
        		}
            }
	}

	augment /rbridge:rbridge-id/interface:interface/interface:ve/ipv6-config:ipv6 {
        when "((/vcs:vcsmode/vcs:vcs-mode = 'true') and 
                (/vcs:vcsmode/vcs:vcs-cluster-mode = 'true'))" {
        }

            list ipv6-local-anycast-gateway {
                key local-ipv6-gw-id;

				leaf local-ipv6-gw-id {
					type uint32 {
              			range "1..255" {
                		}
            		}
        		}

               	uses anycast-gateway-local-common;

        		container ipv6-track {

					list ipv6-interface {
						key "ipv6-interface-type ipv6-interface-name";

						leaf ipv6-interface-type {
							type vrrp:track-iftype;
						}

						leaf ipv6-interface-name {
							type vrrp:track-ifname;
						}

						leaf ipv6-interface-priority {
							type uint32 {
								range "1..254" {
								}
							}
							mandatory true;
							description "Track Priority";
						}
					}

            		list ipv6-network {
                		key "ipv6-network-address";

                		leaf ipv6-network-address {
							type comn:ipv6-address-prefix;
                		}

                		leaf ipv6-network-priority {
                    		type uint32 {
                        		range "1..254" {
                        		}
                    		}
							mandatory true;
                    		description "Track Priority";
                		}
            		}

            		list ipv6-next-hop {
                		key "ipv6-next-hop-address";

                		leaf ipv6-next-hop-address {
                    		type inet:ipv6-address;
                		}

                		leaf ipv6-next-hop-priority {
                    		type uint32 {
                        		range "1..254" {
                        		}
                    		}
							mandatory true;
                    		description "Track Priority";
                		}
            		}
        		}
            }
	}

    grouping anycast-gw-commands {
        leaf enable_global {
            type empty;
        }

        container gratuitous-arp {

            leaf timer {
                type uint32 {
                    range "0..360" {
                    }
                }

                default 0;
            }
        }

        leaf gateway-mac-address {
            type mac-access-list:mac-address-type;
        }
    }

	augment /comn:router {
        when "((/vcs:vcsmode/vcs:vcs-mode = 'true') and 
                (/vcs:vcsmode/vcs:vcs-cluster-mode = 'true'))" {
        }

        container fabric-virtual-gateway {
            //tailf:sort-priority 48;
            presence true;
            description "Fabric virtual gateway";

            container address-family {
                description "Address family";

                container ipv4 {
            		presence true;
                    description "Anycast gateway ipv4";
                    uses anycast-gw-commands;

					leaf accept-unicast-arp-request {
						type empty;
                		description "Accept Unicast Arp Request";
					}
                }

                container ipv6 {
            		presence true;
                    description "Anycast gateway ipv6";
                    uses anycast-gw-commands;
                }
            }
        }
    }
}
