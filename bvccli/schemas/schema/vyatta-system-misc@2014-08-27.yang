module vyatta-system-misc {
	namespace "urn:vyatta.com:mgmt:vyatta-system-misc";
	prefix system-misc;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /system:system {
		container console {
			presence "true";
			configd:priority "100";
			configd:help "Serial console configuration";
			configd:end "/opt/vyatta/share/tmplscripts/system/console/configd_end.sh";
			leaf powersave {
				type empty;
				configd:help "Enable screen blank powersaving on VGA console";
				configd:create "/opt/vyatta/share/tmplscripts/system/console/powersave/configd_create.sh";
				configd:delete "/opt/vyatta/share/tmplscripts/system/console/powersave/configd_delete.sh";
			}
			list device {
				configd:help "Serial console device name";
				configd:end "/opt/vyatta/share/tmplscripts/system/console/device/configd_end.sh";
				key "tagnode";
				leaf tagnode {
					type string {
						pattern "((tty[A-Z])|ttyUSB|(hvc)){1}[0-9]+" {
							configd:error-message "console $VAR(@): not a valid tty name";
						}
					}
					configd:help "Serial console device name";
				}
				leaf modem {
					type empty;
					configd:help "Device is Hayes compatiable modem";
				}
				leaf speed {
					type enumeration {
						enum "1200" {
							configd:help "1200 bps";
						}
						enum "2400" {
							configd:help "2400 bps";
						}
						enum "4800" {
							configd:help "4800 bps";
						}
						enum "9600" {
							configd:help "9600 bps (default)";
						}
						enum "19200" {
							configd:help "19,200 bps";
						}
						enum "38400" {
							configd:help "38,400 bps";
						}
						enum "57600" {
							configd:help "57,600 bps";
						}
						enum "115200" {
							configd:help "115,200 bps";
						}
					}
					configd:help "Console baud rate";
					default "9600";
					configd:allowed "/opt/vyatta/share/tmplscripts/system/console/device/speed/configd_allowed.sh";
				}
			}
		}
		container options {
			presence "true";
			configd:priority "400";
			configd:help "System options";
			leaf reboot-on-panic {
				type boolean;
				configd:help "Reboot system on kernel panic";
				default "true";
				configd:update "/opt/vyatta/share/tmplscripts/system/options/reboot-on-panic/configd_update1.cli";
				configd:delete "/opt/vyatta/share/tmplscripts/system/options/reboot-on-panic/configd_delete1.cli";
			}
		}
	}
}
