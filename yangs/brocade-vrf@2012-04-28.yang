/*********************************************************************
 * brocade-vrf.yang: Brocade VRF module data model
 *
 * Copyright (c) 2011 by Brocade Communications Systems, Inc.
 * All rights reserved.
 *
 ********************************************************************/
module brocade-vrf {
    namespace "urn:brocade.com:mgmt:brocade-vrf";
    prefix "vrf";

    import tailf-common {
        prefix tailf;
    }

    import brocade-rbridge {
        prefix rbridge;
    }

    import ietf-inet-types {
        prefix inet;
    }

	import brocade-common-def {
        prefix common-def;
    }

    organization
        "Brocade Communications Systems, Inc.";

    contact
        "Brocade Communications Systems, Inc.
        Postal: 130 Holger Way
        San Jose, CA 95134
        U.S.A
        Tel: +1-408-333-8000
        E-mail: support@Brocade.com
        web: www.brocade.com.";

    description
        "This module manages Virtual Routing and Forwarding (VRF)";

    revision "2012-04-28" {
        description
            "Initial version of this management module.";
    }

    typedef rd-type {
        type string;
    }

    typedef rt-type {
        type string;
    }

    grouping route-target-config {
        list route-target {
            key "action target-community";
            description
            "Target extended communities. This functionality is not supported
            in NOS4.0.0 release";

            leaf action {
                type enumeration {
                    enum export {
                        value 0;
                    }
                    enum import {
                        value 1;
                    }
                    enum both {
                        value 2;
                    }
                }
            }

            leaf target-community {
                type rt-type;
                description "Target VPN Extended Community";
            }
        }
    }


    grouping vrf-address-family {
        container address-family {
            list ipv4 {
                status deprecated;
                key "max-route";
                leaf max-route {
                    type uint32 {
                        range "128..32000";
                    }
                }
                uses route-target-config {
                    refine "route-target" {
                    }
                }
            }


            container ip {

                container unicast {
                    presence true;
                    leaf max-route {
                        type uint32 {
                            range "1..4294967295";
                        }
                        description "Maximum number of routes allowed in this routing table";
                    }
                }

            }

            container ipv6 {

                container unicast {
                    presence true;
                    leaf max-route {
                        type uint32 {
                            range "1..4294967295";
                        }
                        description "Maximum number of routes allowed in this routing table";
                    }
                }

            }
        }
    }

    grouping vrf-cmds {
        list vrf {
            key vrf-name;
            leaf vrf-name {
                type common-def:vrf-name;
            }
            leaf route-distiniguisher {
                description
                    "Route distinguisher represented in ASN:nn
                    format.";
                type rd-type;
            }
            uses route-target-config;
            uses vrf-address-family;
            container ip {
                leaf vrf-router-id {
                    type inet:ipv4-address;
                }
            }
        }
    }

    augment "/rbridge:rbridge-id" {
        uses vrf-cmds;
    }
}
