/***********************************************************************
 * brocade-vrrpv3.yang: Brocade VRRP v3 data model
 *
 * Oct 2013, Ankit Jindal
 *
 * Copyright (c) 2013 by Brocade Communications Systems, Inc.
 * All rights reserved.
 *
 **********************************************************************/
module brocade-vrrpv3 {
    namespace "urn:brocade.com:mgmt:brocade-vrrpv3";
    prefix "vrrpv3";

    import brocade-rbridge {
        prefix rbridge; 
    }

    import brocade-interface { 
        prefix interface;
    }

    import brocade-ipv6-config {
        prefix ipv6-config;
    }

    import tailf-common { 
        prefix tailf; 
    }

    import ietf-inet-types { 
        prefix inet; 
    }
    organization
        "Brocade Communications Systems, Inc.";

    contact
        "Brocade Communications Systems, Inc.
         Postal: 1745 Technology Drive,
                 San Jose, CA 95110
                  U.S.A
         Tel: +1-408-392-6061
         E-mail: support@Brocade.com
         web: www.brocade.com.";

    description
         "This module describes the data model for Virtual Router Redundancy Protocol";

    revision "2013-10-21" {
        description     
            "Initial version of this management module.";
    }

    typedef vrid-type {
        type uint8 {
            range "1..255" {
                description "Virtual router identifier, Range: 1-255";
            }
        }
    }

    typedef macAddr {
        type string;
    }

    typedef track-iftype {
        type enumeration {
            enum gigabitethernet {
                value 0;
                description "Gigabit Ethernet interface";
             }
            enum tengigabitethernet {
                value 1;
                description "TenGigabit Ethernet interface";
             }
            enum fortygigabitethernet {
                value 2;
                description "FortyGigabit Ethernet interface";
             }
            enum port-channel {
                value 3;
                description "Port-channel interface"; 
             }
            enum hundredgigabitethernet {
                value 10;
                description "HundredGigabit Ethernet interface";
             }
        }
    }

    typedef track-ifname {
        type string {
            pattern '(((([1-9]|[1-9][0-9]|1[0-9]{2}|2[0-3][0-9])/)?'
                    + '(([0-9]|1[0-6]))/([1-9]|[1-9][0-9]))|'
                    + '([1-9]|[1-9][0-9]|[1-9][0-9]{2}|[1-5][0-9]{3}|'
                    + '6[0-1][0-4]{2}))';
        }
    }

    grouping rbridge-cmds {
           container vrrp-rbridge-global {
              leaf vrrp-acceptmode-disable {
                  type empty;
                  description "Disable accept mode  for the non owner vrrp vip";
              }
          }
    }

    grouping global-vrrpv3-cmds {
        container proto-vrrpv3 {
            //tailf:cli-drop-node-name;
            leaf vrrp {
                type empty;
                description "Virtual Router Redundacy Protocol IPv6 (VRRPv3)";
            }
            leaf vrrp-extended {
                type empty;
                    description "Virtual Router Redundacy Protocol IPv6 Extended (VRRPv3-E)";
            }
       }
    }

    grouping vrrpv3-interface-cmds {
        list vrrpv3-group {
            description "Start vrrpv3 configuration";
            key vrid;
            leaf vrid {
                type vrid-type;
            }


            leaf use-v2-checksum {
                type empty;
                description "Use v2 checksum";
            }

            list virtual-ip {
                key virtual-ipaddr;

                leaf virtual-ipaddr {
                    type inet:ipv6-address;
                    description "Virtual IPv6 address";
                }

            /*    leaf auto-link-local {
                    type empty;
                }*/

            }
      
            container track {
                description "Interface to be tracked";

                list interface {
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups-only-cmds;
            uses vrrpv3-groups;
        }
 
        list vrrpv3e-group {
            key vrid;
            leaf vrid {
                type vrid-type;
            }

            list virtual-ip {
                key virtual-ipaddr;
                leaf virtual-ipaddr {
                    type inet:ipv6-address;
                    description "Virtual IPv6 address";
                }
            }

            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups;
            uses vrrpv3e-cmds-only;
        }

        /*list virtual-gateway {
            key vrid;
            leaf vrid {
                type vrid-type;
            }
            uses vrrpv3-vcs-cmds;
        }*/
    }

	container protocol-vrrpv3 {
        description 
            "An intermediary node that separates the protocol vrrpv3 from other protocols.";
        container protocol {
        }
    }

	augment "/rbridge:rbridge-id/rbridge:ipv6" {
        	uses global-vrrpv3-cmds;
		}

    augment "/rbridge:rbridge-id" {
        uses rbridge-cmds;
    }
    
    grouping vrrpv3e-cmds-only {
        leaf advertise-backup {
            type empty;
            description "Enable periodic backup advertisement messages";
        }

        /*leaf vrrpv3e-garp-timer {
            type uint32 {
                range "0..3600";
            }
        }*/

        leaf nd-advertisement-timer {
            type uint32 {
                range "0..3600";
            }
        }

/*        leaf virtual-mac {
            type macAddr;
            description "Virtual mac";
        }*/

        leaf advertisement-interval-scale {
            type uint32 {
                range "1..10" {
                }                
            }
            //default 10; /* TODO: Confirm the default value */
            description "Ipv6 session advertisement interval scale factor <1|2|5|10>";
        
        }

        leaf backup-advertisement-interval {
            type uint32 {
                range "60..3600" {
                }
            }
            //default 60;
            description "Set Backup advertisement interval";
        }

        leaf vrrpe-advertisement-interval {
            type uint32 {
                range "1..255" {
                }
            }
            description "Set advertisement interval";
        }

        container short-path-forwarding {
            description "Enable backup router to send traffic";
			
            leaf basic {
                type empty;
            }

			leaf revert-priority {
				type uint8 {
					range "1..254" {
					}
				}
            	description "Set revert priority";
			}
        }
    }

    grouping vrrpv3-vcs-cmds {
        leaf priority {
            type uint8 {
                range "1..254" {
                }
            }
            //default 100;
            description "Set router priority within virtual router";
        }
    
        leaf description {
            type string {
                length "1..64" {
                    description "Characters describing this interface (Max Size - 64)";
                }
            }
            description "Interface specific description";
        }
    }

     grouping vrrpv3-groups-only-cmds {
        leaf advertisement-interval {
            type uint32 {
                range "100..40900" {
                }
            }
            //default 1;
            description "Set advertisement interval";
        }
     }

    grouping vrrpv3-groups {
        /*leaf advertisement-interval {
            type uint32 {
                range "100..40900" {
                }
            }
            //default 1;
            description "Set advertisement interval";
        }*/

/*
		container enable {
			presence "enable";
            description "Enable Session";

			leaf enable-flag {
                type empty;
                description "Enable Session";
			}
	    }
*/	    
        leaf enable {
            type empty;
            description "Enable Session";
        }

        leaf hold-time {
            type uint32 {
                range "1..3600" {
                }
            }
            description "Configure hold time for this session";
        }

        leaf preempt-mode {
            type empty;
            description "Set preempt mode for the session";
        }
        uses vrrpv3-vcs-cmds;
    }

    augment /interface:interface/interface:tengigabitethernet/interface:ipv6 {
        uses vrrpv3-interface-cmds;
    }
    
    augment /interface:interface/interface:gigabitethernet/interface:ipv6 {
        uses vrrpv3-interface-cmds;
    }
    
    augment /interface:interface/interface:fortygigabitethernet/interface:ipv6 {
        uses vrrpv3-interface-cmds;
    }

    augment /rbridge:rbridge-id/interface:interface/interface:ve/ipv6-config:ipv6 {
        list vrrpv3 {
            key vrid;
            leaf vrid {
                type vrid-type;
            }

            leaf use-v2-checksum {
                type empty;
                description "Use v2 checksum";
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }

            uses vrrpv3-groups-only-cmds;
            uses vrrpv3-groups;
        }

        list vrrpv3e {
            key vrid;
            leaf vrid {
                type vrid-type;
            }

            container virtual-mac {
                description "Virtual MAC";

                leaf vmac {
                    type empty;
                    description "Virtual MAC address";
                }
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups;
            uses vrrpv3e-cmds-only;
        }

        /*list virtual-gateway {
            //tailf:callpoint vrrpv3_vcs_session_vlanintf;
            key vrid;
            leaf vrid {
                type vrid-type;
            }
            uses vrrpv3-vcs-cmds;
        }*/
    }

    // grouping cause yang compiler to crash, forced to duplicate 
    /*augment "/interface:interface-vlan/interface:interface/interface:ve/interface:ipv6" {
        list vrrpv3 {
            key vrid;
            leaf vrid {
                type vrid-type;
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups-only-cmds;
            uses vrrpv3-groups;
        }

        list vrrpv3e {
            key vrid;
            leaf vrid {
                type vrid-type;
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups;
            uses vrrpv3e-cmds-only;
        }

        list virtual-gateway {
            key vrid;
            leaf vrid {
                type vrid-type;
            }
            uses vrrpv3-vcs-cmds;
        }
    }*/

    augment /interface:interface/interface:port-channel/interface:ipv6 {
        container hide-vrrpv3-holder {
        
        list vrrpv3 {
            key vrid;
            leaf vrid {
                type vrid-type;
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups-only-cmds;
            uses vrrpv3-groups;
        }
   
        list vrrpv3e {
            key vrid;
            leaf vrid {
                type vrid-type;
            }

            list virtual-ip {
                key virtual-ipaddr;
                leaf virtual-ipaddr {
                    type inet:ipv6-address;
                    description "Virtual IPv6 address";
                }
            }
      
            container track {
                description "Interface to be tracked";

                list interface {
             
                    key "interface-type interface-name";
                    leaf interface-type {
                        type track-iftype;
                    }

                    leaf interface-name {
                        type track-ifname;
                    }
                
                    leaf track-priority {
                        type uint8 {
                            range "1..254" {
                            }
                        }
                        description "Track Priority";
                    }
                }
            }
            uses vrrpv3-groups;
            uses vrrpv3e-cmds-only;
        }

        /*list virtual-gateway {
            //tailf:callpoint vrrpv3_vcs_session_pointf;
            key vrid;
            leaf vrid {
                type vrid-type;
            }
            uses vrrpv3-vcs-cmds;
        }*/
        }
    }
}
