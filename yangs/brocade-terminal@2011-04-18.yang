/***********************************************************************
 * terminal.yang-: Brocade Terminal Data Model
 *
 * April 2011, Sagar Guntaka
 *
 * Copyright (c) 2011 by Brocade Communications Systems, Inc.
 * All rights reserved.
 *
 **********************************************************************/
module brocade-terminal
{
    namespace "urn:brocade.com:mgmt:brocade-terminal";
        prefix "terminal";
    
    import tailf-common
    {
        prefix tailf;
    }
    organization
         "Brocade Communications Systems, Inc.";

    contact
         "Brocade Communications Systems, Inc.
          Postal: 130 Holger Way
                  San Jose, CA 95134
                   U.S.A
          Tel: +1-408-333-8000
          E-mail: support@Brocade.com
          web: www.brocade.com.";

    description
         "This management submodule is an instrumentation to 
          manage CLI terminal related features.";

    revision "2011-04-18" {
        description
           "Initial version of the management module terminal.";
    }

	typedef terminal-type {
		type enumeration {
            enum vty {
				value 2;
			}
		}
	}

	container terminal-cfg 
	{
		list line 
		{ 
			key "sessionid";
			max-elements 1;

			leaf sessionid {
                type terminal-type;
			}
			leaf exec-timeout {
				type uint32 {
					range "0..136" {
                       error-message "CLI session idle time must be in the 
                                      range 0 - 136 minutes";
					}
				}
			}
		}
	}
}
