/***********************************************************************
 * brocade-Enclosure-show.yang:Yang model for Embedded PLatform Information.
 *
 * 
 *
 * Copyright (c) 2010-2011 by Brocade Communications Systems, Inc.
 * All rights reserved.
 **********************************************************************/
module brocade-Enclosure-show {
	namespace "urn:brocade.com:mgmt:brocade-Enclosure-show";
	prefix "Enclosure-show";


	import tailf-common {
	prefix tailf;
	}

	import brocade-common-def {
	prefix common-def;
	}

	organization
	"Brocade Communications Inc.";

	contact
	"Brocade Communications Systems, Inc.
	Postal: 130 Holger Way
	San Jose, CA 95134             
	U.S.A
	Tel: +1-408-333-6061
	E-mail: support@Brocade.com
	web: www.brocade.com.";

	description
	"This sub module provides interface to Get 
	Enclosure Related information on Embedded paltforms.
	Copyright (c) 2010-2011 by Brocade Communications Systems, Inc.
	All rights reserved.";

	reference
	"";

	augment "/common-def:show" {
	container enclosure {
			description "Provides Embedded Blade Related Information";
				tailf:action slotid {
					description "Provides Present Slot Id of switch";
					input {
					}	
			}	
			tailf:action modelname {
				description "Provided Chassis model name";
                input {
                }
            }
        }
    }
}
