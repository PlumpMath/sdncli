module tailf-netconf-monitoring {
  namespace "http://tail-f.com/yang/netconf-monitoring";
  prefix tncm;

  import ietf-yang-types {
    prefix yang;
  }

  import ietf-netconf-monitoring {
    prefix ncm;
  }

  import tailf-common {
    prefix tailf;
  }

  organization "Tail-f Systems";

  description
    "This module augments ietf-netconf-monitoring with extra
     monitoring data.";

  revision 2012-06-14 {
    description
      "Released as part of ConfD-4,0.

       Fixed a syntax error in a 'when' expression.";
  }

  revision 2012-03-08 {
    description
      "Released as part of ConfD-3.9.

       Added the identities rest-http and rest-https.";
  }

  revision 2011-09-22 {
    description
      "Released as part of ConfD-3.7.

       Added 'transaction-id' leaf.";
  }

  revision 2010-11-04 {
    description
      "Initial revision.

       Released as part of ConfD-3.4.";
  }

  /*
   * Transport Identities
   */

  identity cli-console {
    base ncm:transport;
    description
      "CLI on the console.";
  }

  identity cli-ssh {
    base ncm:transport;
    description
      "CLI over SSH.";
  }

  identity webui-http {
    base ncm:transport;
    description
      "WebUI over HTTP.";
  }

  identity webui-https {
    base ncm:transport;
    description
      "WebUI over HTTPS.";
  }

  identity netconf-tcp {
    base ncm:transport;
    description
      "NETCONF over TCP.";
  }

  identity snmp-udp {
    base ncm:transport;
    description
      "SNMP over UDP.";
  }

  identity rest-http {
    base ncm:transport;
    description
      "REST over HTTP.";
  }

  identity rest-https {
    base ncm:transport;
    description
      "REST over HTTPS.";
  }

  /*
   * File listing for 'file' url.
   */

  augment /ncm:netconf-state {
    container files {
      config false;

      description
        "A list of files available on the server as a 'file' url source
         parameter.";

      tailf:info "files available on the NETCONF server";

      list file {
        key "name";
        leaf name {
          type string;
          description
            "The filename is an absolute path to the file, i.e. it
             always starts with a '/'.";
        }
        leaf creator {
          type string;
          description
            "The name of the user that created the file.  If this
             element is not present, the info is not known to the
             server.";
        }
        leaf created {
          type yang:date-and-time;
          description
            "The time the file was created.  If this element is not
             present, the info is not known to the server.";
        }
        leaf context {
          type union {
            type enumeration {
              enum cli;
              enum netconf;
              enum webui;
            }
            type string;
          }
          description
            "The context used when the file was created.  If this
             element is not present, the info is not known to the
             serber.";
        }
      }
    }
  }

  /*
   * Datastore augmentations
   */

  augment /ncm:netconf-state/ncm:datastores/ncm:datastore {
    when "ncm:name = 'running'";

    leaf transaction-id {
      type string;
      description
        "An opaque string that uniquely identifies the last
         transaction towards the datastore.

         A client can use this to detect if the datastore is
         modified.";
    }
  }

  tailf:annotate "/ncm:netconf-state/tncm:files" {
    tailf:annotate "*" {
      tailf:cli-suppress-show-path;
    }
  }
}
