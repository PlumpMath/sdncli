/***********************************************************************
 * brocade-lldp.yang : Brocade LLDP data model
 *
 * April 2010, Sanjeev C Joshi, Mobin Mohan
 *
 * Copyright (c) 2010 by Brocade Communications Systems, Inc.
 * All rights reserved.
 *
 **********************************************************************/

module brocade-lldp {
    namespace "urn:brocade.com:mgmt:brocade-lldp";
        prefix "lldp";
	
    import tailf-common { prefix "tailf"; }
    
    import brocade-interface {
        prefix interface;
    }
    import brocade-vcs {
        prefix vcs;
    }
    organization
        "Brocade Communications Systems, Inc.";
    
    contact           
        "Brocade Communications Systems, Inc.
         Postal: 1745 Technology Drive,
                 San Jose, CA 95110 
                  U.S.A
         Tel: +1-408-392-6061
         E-mail: support@Brocade.com 
         web: www.brocade.com.";
         
    description       
        "This management module is an instrumentation to manage the 
        'Link Layer Discovery Protocol (LLDP)'. LLDP is a data-link 
        layer protocol, operating above the MAC service layer, that
        performs basic neighbor discovery. The discovering process 
        involves advertising of network device identity, capabilities,
        and interconnections on a IEEE 802 LAN network.
        
        The protocol is formally referred to by the IEEE as Station and 
        Media Access Control Connectivity Discovery specified in 
        standards document 802.1AB.
        
        Glossary of the terms used:
        --------------------------- 
        FCoE - Fibre Channel over Ethernet.
        DCBX - Data Center Bridging Exchange Protocol.
        CEE - Converged Enhanced Ethernet.
        TLV - Type Length Value.";
        
    reference 
        "Tony Jeffree, 'Station and Media Access Control Connectivity 
        Discovery', IEEE 802.1AB-REV, Sept 2009.";        
        
    revision "2010-04-28" {
        description     
            "Initial version of this management module.";
    }         
    
    /* Module Definition */
    grouping lldp-common-config {
        leaf description {
            type string {
				length "1 .. 50";
			}
        }
        
        leaf hello {
            type uint32 {
                range "4..180" {
                }
            }
            units "Seconds.";
			default 30;
        }
        
        leaf mode {
            type enumeration {
                enum tx {
                    value 1;
                }
                enum rx {
                    value 2;
                }
            }

        }
        
        leaf multiplier {
            type uint32 {
                range "2..10" {
                }
            }
			default 4;
        }

        container advertise {
                
            leaf dcbx-fcoe-app-tlv {
            	when "/vcs:vcsmode/vcs:vcs-mode = 'true'";
                type empty;
            }
                    
            leaf dcbx-fcoe-logical-link-tlv {
            	when "/vcs:vcsmode/vcs:vcs-mode = 'true'";
                type empty;
            }       
            
            leaf dcbx-iscsi-app-tlv {
                type empty;
            }

            leaf dcbx-tlv {
                type empty;
            }
            
            leaf dot1-tlv {
                type empty;
            }
            
            leaf dot3-tlv {
                type empty;
            }

            container optional-tlv {
                    
                leaf management-address {
                    type empty;
                }
                
                leaf port-description {
                    type empty;
                }
                
                leaf system-capabilities {
                    type empty;
                }
                
                leaf adv-tlv-system-description {
                    type empty;
                }
                
                leaf adv-tlv-system-name {
                    type empty;
                }
            }
        }
    }
    
	grouping lldp-common-profile-config {
        leaf description {
            type string {
				length "1 .. 50";
			}
        }
        
        leaf hello {
            type uint32 {
                range "4..180" {
                }
            }
            units "Seconds.";
        }
        
        leaf mode {
            type enumeration {
                enum tx {
                    value 1;
                }
                enum rx {
                    value 2;
                }
            }

        }
        
        leaf multiplier {
            type uint32 {
                range "2..10" {
                }
            }
        }

        container advertise {
                
            leaf dcbx-fcoe-app-tlv {
            	when "/vcs:vcsmode/vcs:vcs-mode = 'true'";
                type empty;
            }
                    
            leaf dcbx-fcoe-logical-link-tlv {
            	when "/vcs:vcsmode/vcs:vcs-mode = 'true'";
                type empty;
            }       
            
            leaf dcbx-iscsi-app-tlv {
                type empty;
            }

            leaf dcbx-tlv {
                type empty;
            }
            
            leaf dot1-tlv {
                type empty;
            }
            
            leaf dot3-tlv {
                type empty;
            }

            container optional-tlv {
                    
                leaf management-address {
                    type empty;
                }
                
                leaf port-description {
                    type empty;
                }
                
                leaf system-capabilities {
                    type empty;
                }
                
                leaf adv-tlv-system-description {
                    type empty;
                }
                
                leaf adv-tlv-system-name {
                    type empty;
                }
            }
        }
    }

    grouping common-phy-lldp-cmds {
        container lldp {
                
            container cee {
                description "Generate CEE capable event";
                leaf lldp-cee-on-off {
                    //tailf:hidden debug;
                    //tailf:cli-incomplete-command;
                     type enumeration {
                         enum off {
                             value 0;
                             description "CEE incapable";
                          }
                          enum on {
                             value 1;
                             description "CEE capable";
                         }
                     }
                 }
             }
 
            leaf dcbx-version {
                type enumeration { 
					enum auto { 
                        value 0;
                    }
                    
					enum cee {
                        value 1;
                    }
                    
                    // Defect 372520. Pre-cee not supported from NOS 3.0.0
                    /*enum pre-cee { 
                        value 2;
                    }*/
                    
                }
				default auto;
            }
                
            leaf disable {
                type empty;
            }
                        
            leaf iscsi-priority {

                 type uint32 {
                     range "0..7" {
                     }
                 }
                 default 4;
             }

            leaf profile {
            	type string {
                    pattern '(\S)+';
					length "1..32" {
					}
				}
				mandatory false;
            }
        }

    }
    
    augment "/interface:protocol" {
        container lldp {
			presence true;
                
            uses lldp-common-config;
            
            leaf system-name {
                type string {
					pattern '(([a-zA-Z]{1}([-a-zA-Z0-9\s\.\\\\@#\+\*\(\)=\{~\}%<>=$_\[\]\|]{0,31}))|(\s)*)';
                    length "0..32" {
                    }
                }
				default "";
            }
            
            leaf system-description {
                type string {
                    length "1..50" {
                    }
                }            
            }

            leaf iscsi-priority {
             
                type uint32 {
                    range "0..7" {
                    }
                }
				default 4;
            }

            leaf disable {
                type empty;
            }

            list profile {
                key profile-name;
                    
                leaf profile-name {
                    type string {
                        pattern '(\S)+';
                        length "1..32" {
                        }
                    }
                }

                uses lldp-common-profile-config;
            }
        }
    }

    augment "/interface:interface/interface:tengigabitethernet" {
        uses common-phy-lldp-cmds;
    }

    augment "/interface:interface/interface:gigabitethernet" {
        uses common-phy-lldp-cmds;
    }

    augment "/interface:interface/interface:fortygigabitethernet" {
        uses common-phy-lldp-cmds;
    }

    augment "/interface:interface/interface:hundredgigabitethernet" {
        uses common-phy-lldp-cmds;
    }
}
