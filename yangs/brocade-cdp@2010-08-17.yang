/***********************************************************************
 * brocade-cdp.yang : Brocade CDP data model
 *
 * April 2010, Mobin Mohan
 *
 * Copyright (c) 2010 by Brocade Communications Systems, Inc.
 * All rights reserved.
 *
 **********************************************************************/

module brocade-cdp {
    namespace "urn:brocade.com:mgmt:brocade-cdp";
        prefix "cdp";
	
    import tailf-common { 
        prefix "tailf"; 
    }
    
    import brocade-interface {
        prefix interface;
    }
    
    organization
        "Brocade Communications Systems, Inc.";
    
    contact           
        "Brocade Communications Systems, Inc.
         Postal: 1745 Technology Drive,
                 San Jose, CA 95110 
                  U.S.A
         Tel: +1-408-392-6061
         E-mail: support@Brocade.com 
         web: www.brocade.com.";
         
    description       
        "This management module is an instrumentation to manage the 
        'Cisco Discovery Protocol (CDP)'.";
        
    revision "2010-08-17" {
        description     
            "Initial version of this management module.";
    }         
    
    augment "/interface:protocol" {
        container cdp {
			presence true;
        }
    }
}
