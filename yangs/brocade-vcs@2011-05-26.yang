/***********************************************************************
 * brocade-vcs.yang: Brocade VCS Cluster Data Model
 *
 * April 2011, Brian Adaniya, Sanjeev C Joshi
 *
 * Copyright (c) 2011 by Brocade Communications Systems, Inc.
 * All rights reserved.
 *
 **********************************************************************/
module brocade-vcs {
    namespace "urn:brocade.com:mgmt:brocade-vcs";
    prefix "vcs";
   
    import tailf-common {
        prefix tailf; 
    }

    import ietf-inet-types { 
        prefix inet; 
    }

    import ietf-yang-types { 
        prefix yang; 
    }
    
    import brocade-common-def {
        prefix common-def;
    }
  
    organization
        "Brocade Communications Systems, Inc.";

    contact           
        "Brocade Communications Systems, Inc.
         Postal: 130 Holger Way
                 San Jose, CA 95134
                  U.S.A
         Tel: +1-408-333-8000
         E-mail: support@Brocade.com 
         web: www.brocade.com.";

    description        
        "This management module is an instrumentation to manage  
        Virtual Cluster Switching (VCS).
        
        Glossary of the terms used:
        --------------------------- 
        VAL  - Virtual Access Layer, provided by VCS.
        VCS  - Virtual Cluster Switching.
        TRILL - Transparent Interconnection of Lot of Links.
        TLS - Transparent LAN Services.
        
        
        VCS refers to the ability of a group of physical Ethernet 
        switches, inter-connected in arbitrary fashion via the regular 
        front-end data ports, to present themselves as one unified and
        transparent Ethernet switching service to the external network. 
        The inter-connecting network that glues all these individual 
        switches is refered as 'fabric', and the group of physical 
        Ethernet switches in the fabric is refered to as 'cluster'. 
        
         +--------+                                   +--------+
         |External|                                   |External| 
         |Non-VCS |                                   |Non-VCS |
         |Switch  |                                   |Switch  |
         +--------+                                   +--------+          
           |                                              |
           |                                              |
           |                                              |
         +---+                                            |          
         |   |                                            | 
         |S1 |                                      ******************
         +---+                                      * Logical Switch *  
           |<------ Fabric Port    \---->           *                *  
           |                       /---->           * (VCS Cluster)  *
         +---+                                      ******************
         |   |                                            |
         |S2 |                                            |
         +---+                                            |
           |<----- Edge Port                              |
           |                                              |
         +-------+                                   +-------+
         |Server |                                   |Server |
         +-------+                                   +-------+
         
         [Physical View]                            [Logical View]
         
        As shown in the figure above, the fabric ports are transparent 
        as far as the external devices connected to the VCS are 
        concerned. In this sense the whole of the cluster behaves like 
        a logical switch to the external network.         
        ";
        
    revision "2011-05-26" {
        description
            "Initial version of this management module.";
    }

	typedef vcs-cluster-type {
		type enumeration {
			enum vcs-unknown-cluster {
                value 1; 
                description 
                    "Unknown cluster mode.";
            }
			enum vcs-stand-alone {
                value 2;
                description 
                    "Stand-alone mode. No VCS services are enabled.";
            }
			enum vcs-fabric-cluster {
                value 3; 
                description 
                    "Fabric-cluster mode. VCS services are enabled.";
            }
			enum vcs-management-cluster { 
                value 4; 
                description
                    "Management-cluster mode. VCS services are enabled 
                    with cluster-wide configuration distribution 
                    capability.";
            }
		}
		description
			"Category of VCS Cluster
				vcs-unknown-cluster    - Unknown cluster 
				vcs-stand-alone        - VCS is in stand alone
				vcs-fabric-cluster     - Fabric cluster 
				vcs-management-cluster - Management cluster
			";
	}

    typedef node-hw-sync-state-type {
        type enumeration {
            enum node-unknown {
                value 1; 
                description 
                    "'Unknown' state.";
            }
            enum node-uninitialized { 
                value 2;
                description
                    "'Uninitialized' state.";
            }
            enum node-synchronizing { 
                value 3; 
                description 
                    "'Synchronizing' state.";
            }
            enum node-in-sync { 
                value 4; 
                description 
                    "'In-Sync' state.";
            }
            enum node-out-of-sync { 
                value 5; 
                description 
                    "'Out of sync' state.";
            }
        }

        description
            "Category of node hardware synchronization states
                node-unknown        - Unknown
                node-uninitialized  - Uninitialized
                node-synchronizing  - Synchronizing
                node-in-sync        - In sync
                node-out-of-sync    - Out of sync
            ";
    }
    
    typedef node-state-type {
        type enumeration {
            enum Unknown {
                value 1;
                description
                    "'Unknown' state.";
            }
            enum Online {
                value 2;
                description
                    "'Co-ordinator' or 'Connected to Cluster'.";
            }
            enum Offline {
                value 3;
                description
                    "Disconnected From Cluster.";
            }
            enum Replacing {
                value 4;
                description
                    "Switch Replacement In Progress.";
            }
            enum Coming-Online {
                value 5;
                description
                    "Coming Online.";
            }
            enum Rejoining {
                value 6;
                description
                    "Rejoining.";
            }
            enum Awaiting-Rejoin {
                value 7;
                description
                    "Awaiting Rejoin.";
            }
        }

        description
            "Category of node states
                unknown          - 'Unknown' state
                online           - 'Co-ordinator' or 'Connected to Cluster'
                offline          - Disconnected From Cluster
                replacing        - Switch Replacement In Progress
                coming-online    - Coming Online
                rejoining        - Rejoining
                awaiting-rejoin  - Awaiting Rejoin
            ";
    }

    typedef snapshot-id-all-type {
            type string ;
    } 

    typedef snapshot-id-type {
            type string {
                pattern "[a-zA-Z0-9]{1,50}";
            }
    }

    typedef ve-type {
        type uint32 {
            range "1..8191" {
            }
        }
        description
            "The definition for specifying a ve identifier.";
    }

    container vcsmode {

        leaf vcs-mode {
            type boolean;
            mandatory true;
        }
        leaf vcs-cluster-mode {
            type boolean;
            mandatory true;
        }
    }

    container local-node {

        leaf swbd-number {
            type uint32;
            mandatory true;
        }
    }
								 
    rpc get-last-config-update-time {
        description
            "This rpc function provides time-stamp of the last 
            configutation change done on the managed device.";
        output {
            leaf last-config-update-time {
                type uint64;
                description
                    "This leaf indicates the time-stamp of the last 
                    configuration change on the system.";
            }
        }
    }

    grouping vcs-general-info-grouping {
        leaf principal-switch-wwn {
            type string;
            description 
                "Vcs Cluster Co-ordinator node wwn";
        }
        leaf co-ordinator-wwn {
            type string;
            description
                "Vcs Cluster Co-ordinator node wwn";
        }
        leaf vcs-cluster-type-info {
            type vcs-cluster-type;
            description 
                "Vcs Type";
        }
        leaf vcs-guid {
            type string;
            description "Vcs Cluster GUID";
        }
        leaf virtual-ip-address {
            type string;
            description 
                "Cluster virtual IP address";
        }
        leaf total-nodes-in-cluster {
            type uint16;
            description 
                "Total number of nodes in cluster";
        }
        leaf nodes-disconnected-from-cluster {
            type uint16;
            description 
                "Number of nodes disconnected from cluster";
        }
        leaf cluster-generic-status {
            type string;
            description 
                "Cluster Generic Status";
        }
        leaf cluster-specific-status {
            type string;
            description 
                "Cluster Specific Status";
        }
    }

    grouping vcs-node-info-grouping {
        list vcs-node-info {
            leaf node-num {
                type uint16;
                description 
                    "Node number";
            }
            leaf node-serial-num {
                type string;
                description 
                    "Serial number";
            }
            leaf node-condition {
                type string;
                description 
                    "Node condition";
            }
            leaf node-status {
                type string;
                description 
                    "Node status";
            }
            leaf node-hw-sync-state {
                type node-hw-sync-state-type;
                description 
                    "Node hardware synchronization state";
            }
            leaf node-vcs-mode {
                type string;
                description 
                    "Node's VCS mode";
            }
            leaf node-vcs-id {
                type uint16;
                description 
                    "Node VCS id";
            }
            leaf node-rbridge-id {
                type uint16;
                description 
                    "Node rbridge Id";
            }
            leaf node-is-principal {
                type boolean;
                description 
                    "Whether node is management cluster principal.";
            }
            leaf co-ordinator {
                type boolean;
                description
                    "Whether node is management cluster co-ordinator.";
            }
            leaf node-switch-mac {
                type yang:mac-address;
                description 
                    "Node switch mac address";
            }
            leaf node-switch-wwn {
                type string;
                description 
                    "Node switch WWN";
            }
            leaf switch-fcf-mac {
                type yang:mac-address;
                description 
                    "Node fcf mac address";
            }
            leaf node-internal-ip-address {
                type inet:ipv4-address;
                description 
                    "Node internal IP address";
            }
            list node-public-ip-addresses {
                leaf node-public-ip-address {
                    type inet:ipv4-address;
                    description 
                        "Node public ip address";
                }
            }
            list node-public-ipv6-addresses {
                leaf node-public-ipv6-address {
                    type inet:ipv6-address;
                    description
                        "Node public ipv6 address";
                }
            }
            leaf firmware-version {
                type string;
                description 
                    "Node Firmware version";
            }
            leaf node-swbd-number {
                type int32;
                description 
                    "Node SWBD number.";
            }
            leaf node-switchname {
                type string;
                description 
                    "Node switchname.";
            }
            leaf node-switchtype {
                type string;
                description 
                    "Node switchtype.";
            }
            leaf node-state {
                type node-state-type;
                description
                    "Node state";
            }
            leaf node-fabric-state {
                type string;
                description
                    "Fabric node state";
            }
        }
    }

    rpc show-vcs {
        output {
            uses vcs-general-info-grouping;
            container vcs-nodes {
                uses vcs-node-info-grouping;
            }
        }
    }

	rpc get-vcs-details {
		output {
			container vcs-details {
				leaf principal-switch-wwn {
					type string;
					description
						"WWN of principal switch";
				}
                leaf co-ordinator-wwn {
                    type string;
                    description
                        "WWN of Co-ordinator switch";
                }
				leaf local-switch-wwn {
					type string;
					description
						"WWN of local switch";
				}
				leaf node-vcs-mode {
                	type boolean;
                	description 
                        "Node's VCS mode";
				}
				leaf node-vcs-type {
					type vcs-cluster-type;
					description
						"Vcs Type";
				}
				leaf node-vcs-id {
					type uint32;
					description
						"Vcs Id";
				}
			}
		}
	}

    rpc vcs-rbridge-context {
        input {
            leaf rbridge-id {
                type uint16 {
                    range 1..239 {
                        error-message 
                            "rbridge-id must be in the range 1..239";
                    }
                }
            }
        }
    }

    rpc no-vcs-rbridge-context {
    }
    
    rpc get-last-config-update-time-for-xpaths {
        input {
            list xpath-strings {
                key xpath-string;
                leaf xpath-string {
                    type string;
                }
            }
        }
        output {
            list last-config-update-time-for-xpaths {
                key xpath-string;
                leaf xpath-string {
                    type string;
                }
                leaf last-config-update-time {
                    type uint64;
                }
            }
        }
    }

	container vcs {

        container virtual {

            container ip {
                list address {

                    key "address";
                    leaf address {
                        type common-def:ipv4-address-prefix-type;       
                    }

                    container inband {
                        container interface {
                            leaf ve {
                                type ve-type;
                            }
                        }
                    }
                }
            }
			container ipv6 {
				list address {

					key "ipv6address";
					leaf ipv6address {
						type common-def:ipv6-address-prefix;
					}
				}
			}
        }

        container virtual-fabric {
            description "Vcs Virtual Fabric configuration";
            leaf vfab-enable {
                description "Enable virtual fabric"; 
                type empty;
            }
        }
    }
}
