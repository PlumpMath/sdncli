/***********************************************************************
 * brocade-system-monitor-ext.yang: data model for show system-monitor
 *
 * May 2011, Newton Oku
 *
 * Copyright (c) 2011 by Brocade Communications Systems, Inc.
 * All rights reserved.
 *
 **********************************************************************/
module brocade-threshold-monitor-ext {
    namespace "urn:brocade.com:mgmt:brocade-threshold-monitor-ext";
    prefix "threshold-monitor-extensions";
  
    import tailf-common {
        prefix tailf;
    }

    import brocade-common-def {
        prefix common-def;
    }


    organization
        "Brocade Communications Inc.";

    contact
        "Brocade Communications Systems, Inc.
         Postal: 130 Holger Way
                 San Jose, CA 95134
                 U.S.A
         Tel: +1-408-333-6061
         E-mail: support@Brocade.com
         web: www.brocade.com.";

    description
        "This sub module defines show threshold-monitor data model
         Copyright (c) 2011 by Brocade Communications Systems, Inc.
         All rights reserved.";

    revision 2011-05-05 {
        description
          "Initial version of this module.";
    }

	typedef threshold-monitor-state-enum {
		type enumeration {
			enum No-Change {
				value 0;
			}
			enum In-Range {
				value 1;
			}
			enum Out-Of-Range {
				value 2;
			}
		}
	}
	typedef threshold-monitor-pause-enum {
		type enumeration {
			enum Paused {
				value 0;
			}
			enum Monitoring {
				value 1;
			}
		}
	}

	typedef threshold-monitor-area {
		type enumeration {
			enum MissingTerminationCharacter {
				value 0;
			}
			enum CRCAlignErrors {
				value 1;
			}
			enum SymbolErrors {
				value 2;
			}
			enum IFG {
				value 3;
			}
			enum CFI {
				value 4;
			}
		}
	}
    typedef sfp-type {
		type enumeration {
			enum 1GSR {
				value 0;
			}
			enum 1GLR {
				value 1;
			}
			enum 10GSR {
				value 2;
			}
			enum 10GLR {
				value 3;
			}
			enum 10GUSR {
				value 4;
			}
			enum QSFP {
				value 5;
			}

		}
	}
/*    augment "/common-def:show" {
        container threshold {
            tailf:action monitor {
				input {
					leaf interface {
						type string;
					}

					leaf area {
						type threshold-monitor-area;
					}
				}
				output {
					list thresholdmonitor-interface {
						leaf interface-name {
							type string;
						}
						leaf area {
							type threshold-monitor-area;
						}
						leaf value {
							type uint32;
						}
						leaf status {
							type threshold-monitor-state-enum;
						}
						leaf monitor-status { 
							type threshold-monitor-pause-enum;
						}
					}
            	}
        	}
		}
	}
*/
	augment "/common-def:show/common-def:defaults" {
		container threshold {
			tailf:action sfp {
				input {
					leaf type {
						mandatory true;
						type sfp-type;
					}

				}
			}
			tailf:action interface {
				input {
					leaf type {
						mandatory true;
						type enumeration {
							enum Ethernet{
								value 0;
							}
						}
					}
				}
			}
			tailf:action security {
			}
		}
	}
}
//}
/*
    rpc show-system-monitor {
        input {
            leaf rbridge-id {
                mandatory false;
                type common-def:rbridge-id-all-type;
            }
        }
        output {
            list switch-status {
                leaf rbridge-id-out {
                    type common-def:rbridge-id-type;
                }
                leaf switch-name {
                    type string;
                    description "name of the switch";
                }
                leaf switch-ip {
                    type inet:ip-address;
                    description "ip address of the switch";
                }
                leaf report-time {
                    type ietfyang:date-and-time;
                    description "switch report timestamp";
                }
                leaf switch-state {
                    type system-monitor-health-state-enum;
                    description "switch status based on components";
                }
                leaf switch-state-reason {
                    type string;
                    description "component reason for switch status";
                }
                list component-status {
                    leaf component-name { 
                        type string;
                        description "component name";
                    }
                    leaf component-state { 
                        type system-monitor-health-state-enum;
                        description "component status based on thresholds";
                    }
                }
                list port-status {
                    leaf port-area {
                        type uint32;
                        description "port identifier";
                    }
                    leaf port-name {
                        type string;
                    }
                    leaf port-state {
                        type system-monitor-port-state-enum;
                        description "port state";
                    }
                }
            }
        }
    }
*/
