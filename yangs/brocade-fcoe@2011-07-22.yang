/***********************************************************************
 *brocade-fcoe.yang-: Brocade FCoE Data Model
 *
 *  Jul 2011,Vikas Dharwadkar
 *
 * Copyright (c) 2011 by Brocade Communications Systems, Inc.
 * All rights reserved.
 *
 **********************************************************************/
module brocade-fcoe {
    namespace "urn:brocade.com:mgmt:brocade-fcoe";
    prefix "fcoe";
    import tailf-common {
        prefix tailf;
    }
    import brocade-rbridge { 
        prefix rbridge; 
    }
    import brocade-common-def {
        prefix common-def;
    }
    import brocade-interface {
        prefix interface;
    }
    organization
        "Brocade Communications Systems, Inc.";

    contact           
        "Brocade Communications Systems, Inc.
         Postal: 130 Holger Way
                 San Jose, CA 95134
                  U.S.A
         Tel: +1-408-333-8000
         E-mail: support@Brocade.com 
         web: www.brocade.com.";

    description       
        "This management module is an instrumentation to manage fcoe  
         feature.
         
         Fiber Channel over Ethernet (FCoE) is an
         encapsulation of Fiber Channel frames over Ethernet networks. 
         This allows Fiber Channel to use 10 Gigabit Ethernet networks
         (or higher speeds) while preserving the Fiber Channel protocol.

         The FCoE interface can be managed using this module.

         This module provides a mechanism to configure FCoE maps and
         FCoE interface.
          
         Glossary of the terms used
         --------------------------  
         FIP -      FCoE Initialization Protocol is the standard for
                    initialization of FCoE network.   
         VFID -     Virtual Fabric Identifier
        ";

    reference
        "The FC-BB-5 standard ANSI/INCITS 462-2010.";

    revision "2011-07-22" {
        description     
            "Initial version of the management module brocade-fcoe.";
    }

    typedef fcoe-fcmap-type {
        type string {
            pattern '[0][Ee]:[Ff][Cc]:[0-9a-fA-F]{2}';
            length "1..9" {
                description
                    "This indicates the minimum and maximum length of
                     characters that can be specified for FC map.";
            }
        }
       description
           "The definition for specifying FCoE FC map.";
    }

    typedef fcoe-vlan-type {
        type int32 {
            range "2..4090" {
                description
                    "The indicates the range of values that can be 
                     specified for FCoE VLAN.";
            }
        }
        description
            "The definition for specifying FCoE VLAN.";
    }

    typedef fcoe-vfid-type {
        type int32 {
            range "1..4096" {
                description
                    "This indicates the range of values that can be
                     specified for  Virtual Fabric ID.";
            }
        }
        description
            "The definition for specifying virtual fabric ID.";  
    }

    typedef fcoe-fabric-map-name-type {
        type string {
            pattern 'default';
            length "1..32" { 
                description
                    "This indicates the minimum and maximum number of
                     characters that can be specified for 
                     FCoE Fabric map name.";
            }
        }
        description
            "The definition for specifying FCoE Fabric name.";
    }
    typedef fcoe-enode-fabric-map-name-type {
        type string {
            pattern 'default';
            length "1..32" { 
                description
                    "This indicates the minimum and maximum number of
                     characters that can be specified for 
                     FCoE Fabric map name.";
            }
        }
        description
            "The definition for specifying FCoE Enodes Fabric name.";
    }

    typedef fcoe-map-name-type {
        type string {
             pattern 'default';
            length "1..32" {
                description
                    "This indicates the minimum and maximum number of 
                     characters that can be specified for FCoE Map 
                     name.";   
            }
        }
        description
            "The definition for specifying FCoE Map name.";   
    }

    typedef fcf-map-name-type {
        type string {
            //pattern 'default | sanA | sanB';
            length "1..32" {
                description
                    "This indicates the minimum and maximum number of
                     characters that can be specified for FCF Map
                     name.";
            }
        }
        description
            "The definition for specifying FCF Map name.";
    }

    typedef fcoe-cee-map-name-type {
        type string {
            length "1..32" {
                description
                    "This indicates the minimum and maximum number of 
                     characters that can be specified for CEE map
                     name.";   
            }
        }
        description
            "The definition for specifying CEE map name.";
    }

    typedef fcoe-priority-type {
        type int32 {
            range "0..6" {
                description
                    "This indicates the range of values that can be
                     specified for FCoE priority.";  
            }
        }
        description
            "The definition for specifying the FCoE priority."; 
    }

    typedef interface-fcoe-type {
        type string {
            length "3..32" {
                description
                    "This indicates the maximum and minimum length of
                     characters that can be specified for 
                     FCoE interface.";
            }
        }
        description
            "The definition for FCoE interface.The FCoE 
             interface can be specified in the 'VN-Num/Rbridge/port' 
             format.";       
    }
    /*
     * typedef fcoe-mtu-type {
     *   type int32 {
     *       range "100..2500" {
     *           description "MTU:100-2500;;Enter the mtu value";
     *       }
     *   }
     * }
     */

    typedef fcoe-max-enodes-type {
        type uint32 {
            range "256..1000" {
                description "NUMBER:256-1000;;Enter the max-enodes count";
            }
        }
    }
    typedef fcoe-max-enodes-per-rbridge-type {
        type uint32 {
            range "0..1000" {
                description "NUMBER:0-1000;;Enter fcoe max-enodes ";
            }
        }
    }

    typedef fcoe-enodes-cfg-type {
        type string {
            pattern 'global|local';
            length "1..6" {
                description
                    "This indicates the mode of Enodes configuration.";
            }
        }
       description
           "The definition for specifying FCoE Enodes config mode.";
    }

    /* Let us group the FIP config commands, so that they can
     * be used in the FCoE-FIP, FCoE-FABRIC-MAP, INTF submodes
     */
    grouping fcoe-fip-config-cmd-set {
        container fcoe-fip-advertisement {
            description
                "This provides the grouping of all FIP configuration
                 elements."; 
            leaf fcoe-fip-advertisement-interval {
                type int32 {
                    range "250..90000" {
                        description
                            "This indicates the range of values that can 
                             be specified for FIP advertisement 
                             interval.";
                    }
                }
                description
                    "This specifies the FCoE advertisement interval.";
            }
        }
        
        container fcoe-fip-keep-alive {
            description 
                "This provides the grouping of FCoE keep alive
                 configuration elements.";
                 
            leaf fcoe-fip-keep-alive-timeout {
                type empty;
                description
                    "This specifies if the keep alive timeout should
                     be enabled.

                     The presence of this leaf specifies that FIP
                     keep-alive timeout is enabled.";    
            }
        }
    }

    container fcoe-fsb {
		/* removing the hidden check */
        /* tailf:hidden debug; */
        description
            "This CLI will disable/enable fsb mode";

        leaf fcoe-fsb-enable {
            type empty;
            description
                 "The presence of this leaf specifies that fsb
                 mode is enabled.";
        }
    }

    container fcoe {
        description
            "This provides the grouping of all FCoE map configuration
             elements.";

        list fcoe-fabric-map {
            key fcoe-fabric-map-name;

            description
                "List of FCoE fabric map parameters.";

            leaf fcoe-fabric-map-name {
                type fcoe-fabric-map-name-type;
                // type common-def:name-string32; // this should be changed when support multiple sans
                description
                    "This specifies the name for the FCoE fabric map.";
            }
            
            leaf fcoe-fabric-map-vlan {
                type fcoe-vlan-type;
                description
                    "This specifies the VLAN for the FCoE Fabric Map.";
            }
            
            leaf fcoe-fabric-map-priority {
                type fcoe-priority-type;
                description
                    "This specifies the priority for the FCoE
                     Fabric-map.";  
            }

            leaf fcoe-fabric-map-virtual-fabric {
                type fcoe-vfid-type;
                description
                    "This specifies the Virtual Fabric ID for the 
                     Fabric-map.";
            }

            leaf fcoe-fabric-map-fcmap {
                type "fcoe-fcmap-type";
                description
                    "This specifies the FCMAP value for a FCoE
                     Fabric-map.";
            }

            /* Add all the FIP configuration commands to the VLAN 
               submode */

            /*
             *leaf fcoe-fabric-map-mtu {
             *   tailf:alt-name mtu;
             *   description "Configure the MTU value for a FCOE Fabric-map";
             *   type "fcoe-mtu-type";
             *}
             */


            uses fcoe-fip-config-cmd-set;
        }

        list fcoe-map {
            key fcoe-map-name;
            description
                "The list of FCoE maps.Each row contains the FCoE map
                 name and the list of FCoE fabric maps and CEE maps.";

            leaf fcoe-map-name {
                type fcoe-map-name-type;
                // type common-def:name-string32;
                description
                    "This specifies the FCoE map name.";
            }
        
            list fcoe-map-fabric-map {
                key fcoe-map-fabric-map-name;
                description
                    "List of FCoE Fabric map in the FCoE map. Each row
                     represents Fabric Map name.";

                leaf fcoe-map-fabric-map-name {
                    type fcoe-fabric-map-name-type;
                    description
                        "This specifies the FCoE fabric map name.";
                }
            }


        /*
            container fcoe-map-fabric-map {
                description
                    "List of FCoE Fabric map in the FCoE map. Each row 
                     represents Fabric Map name.";
 
                leaf-list fcoe-map-fabric-map-name {
                // type common-def:name-string32;
                    type fcoe-fabric-map-name-type;
                    description
                        "This specifies the FCoE fabric map name.";
                }
            }
        */
           
            container fcoe-map-cee-map {
                description
                    "This provides the grouping for FCoE CEE map
                     configuration elements.";
                
                leaf fcoe-map-cee-map-leaf {
                    type fcoe-cee-map-name-type;
                    description 
                        "This specifies the CEE Map in the FCoE map.";
                }
            }
        }

        list fcoe-fcf-map {
            key fcf-map-name;
            description
                "The list of FCF maps. Each row contains the FCF map
                 name, member FCoE map, FCF rbid and FDF rbids";

            leaf fcf-map-name {
                type fcf-map-name-type;
                description
                    "This specifies the FCF map name.";
            }

        uses fcoe-fcf-map-cmds;

        }
    }

    grouping fcoe-fcf-map-cmds {
        container fcf-map-fcoe-map {
            description
                "This provides the FCoE map configuration
                 elements in FCF map";

            leaf fcf-map-fcoe-map-leaf {
                type fcoe-map-name-type;
                description
                    "This specifies the FCoE Map in the FCF map.";
            }
        }

        leaf fcf-map-ag-rbid {
            type uint32;
            description
                "This specifies the FCF's rbridge-id in the
                 FCF Map";
        }

/*
        list fcf-map-fdf-rbid {
            key fcf-map-fdf-rbid-num;
            description
                "List of FDF rbridge-ids in the FCFmap. Each row
                 represents an FDF rbridge.";
             leaf fcf-map-fdf-rbid-num {
                type uint32;
                description
                    "This specifies the FDF rbridge-id";
            }
        }
*/

    }

    augment "/interface:interface" {
        list fcoe {
            key fcoe-interface-name;
            description
                "The list of FCoE interfaces. Each row contains FCoE
                 interface name and its status.";
            
            leaf fcoe-interface-name {
				type interface-fcoe-type;
			
                // type interface:fcoe-interface-range; 
			
                description
                    "This specifies the FCoE interface name.";
            }
            
            leaf fcoe-interface-shutdown {
                type empty;
                description
                    "This specifies, if the FCoE interface is enabled
                     or not. 
                     The presence of this leaf indicates the 
                     interface is shutdown.";
            }

            container fcoe-interface-bind {
                description "Bind the FCoE interface to a Physical Ethernet Port.";
                choice fcoe-interface-bind-type {
					case fcoe-interface-bind-te {
						leaf fcoe-interface-bind-te {
							type empty;
							description
								"Bind to TenGigabitEthernet port";
						}
					}
					case fcoe-interface-bind-fo {
						leaf fcoe-interface-bind-fo {
							type empty;
							description
								"Bind to FortyGigabitEthernet port";
						}
					}
					case fcoe-interface-bind-po {
						leaf fcoe-interface-bind-po {
							type empty;
							description
								"Bind to Port-channel";
						}
					}
					case fcoe-interface-bind-mac {
						leaf fcoe-interface-bind-mac {
							type empty;
							description
								"Bind to an Enode Mac-address";
						} 
					} 
					case fcoe-interface-bind-hu {
						leaf fcoe-interface-bind-hu {
							type empty;
							description
								"Bind to HundredGigabitEthernet port";
                        }
                    }
                }

                leaf fcoe-interface-bind-name {
                    description "Interface name or Enode mac address";
                    type string {
                        length "0..32" {
                            description
                                "This indicates the interface bind value.
                                 Bind value can be a Physical or Logical 
                                 Ethernet interface or a Mac-Address.";
                        }
                    }
                    default "";
                }
            }
        }
    }

    grouping fcoeport-lag-commands {
        container fcoeport {
            leaf fcoeport-map {
                type fcoe-map-name-type;
            }
        }
    }


    grouping fcoeport-commands {
        container fcoeport {
            description 
                "This provides the grouping for FCoE configuration
                 elements on a port.";
            leaf fcoeport-map {
                type fcoe-map-name-type;
                description
                    "This specifies the name of the FCoE map.";
            }
        }
    }

    augment "/interface:interface/interface:port-channel" {
        uses fcoeport-lag-commands;
    }
    
    grouping fabric-commands {
         container fabric {
            description "Configure the Fabric Protocol parameters";
            container fabric-isl {
                description "Configure the Fabric Protocol ISL parameters";
	            leaf fabric-isl-enable {
	                description "Configure the Fabric Protocol ISL status";
	                type empty;
	            }
	        }
	        container fabric-trunk {
	            description "Configure the Fabric Protocol Trunk parameters";
	            leaf fabric-trunk-enable {
	                description "Configure the Fabric Protocol Trunk status";
	                type empty;
	            }
	        }
            container neighbor-discovery {
				//tailf:hidden neighbor-discovery;
                description "Neighbor discovery at this port";
                leaf disable {
					description
						"Disable neighbor discovery at this port";
					type empty;
				}
            }
        }
    }


	grouping fcoe-rbridge-commands {
		container fcoe-config {
	 		 description
		  		"This provides the grouping of all FCoE map configuration
		  			elements.";

	 	 	list fcoe-enode-fabric-map {
				key fcoe-enode-fabric-map-name;
			  	description
				  "List of FCoE fabric map parameters.";

	  			leaf fcoe-enode-fabric-map-name {
		  			type fcoe-enode-fabric-map-name-type;
	 				description
		  				"This specifies the name for the FCoE fabric map.";
	  			}
/*
	  			leaf fcoe-max-enode {
	 			type fcoe-max-enodes-per-rbridge-type;
				description
					"This specifies the Number of the FCoE Enodes.";

				} */
	  		}
	  			leaf fcoe-max-enode {
	 			type fcoe-max-enodes-per-rbridge-type;
				description
					"This specifies the Number of the FCoE Enodes.";
		}
    }
  }


    augment /interface:interface/interface:fortygigabitethernet {
        uses fabric-commands {
             refine "fabric/neighbor-discovery" {
             }
		}

		uses fcoeport-commands;
    }

    augment /interface:interface/interface:hundredgigabitethernet {
        uses fabric-commands {
             refine "fabric/neighbor-discovery" {
             }
        }

        uses fcoeport-commands;
    }


    augment "/interface:interface/interface:tengigabitethernet" {
        uses fabric-commands {
             refine "fabric/neighbor-discovery" {
             }
		}
        
        uses fcoeport-commands;
	}

    augment "/interface:interface/interface:gigabitethernet" {
		container fabric {
            container neighbor-discovery {
				//tailf:hidden neighbor-discovery;
                description "Neighbor discovery at this port";
                leaf disable {
					description
						"Disable neighbor discovery at this port";
					type empty;
				}
            }
		}
	}
   augment "/rbridge:rbridge-id" {
       uses fcoe-rbridge-commands;
   }
}
