/**********************************************************************
 * brocade-mac-access-list.yang: Brocade MAC access list data model
 *
 * March 2011, Pasupathi Duraiswamy
 *
 * Copyright (c) 2011 by Brocade Communications Systems, Inc.
 * All rights reserved
 *
 *********************************************************************/
module brocade-mac-access-list {
    namespace "urn:brocade.com:mgmt:brocade-mac-access-list";
    prefix mac-access-list;


    import tailf-common { 
        prefix tailf;
    }

    import brocade-interface {
       prefix interface;
     
    }

    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "This management sub-module contains the configuration
        and rpc implementaion for MAC Access-list.";

    revision "2011-02-28" {
       description "Initial Version with rpc";
    }

    typedef mac-address-type {
        type string;
    }

    typedef src-dst-mac-address-mask-type {
        type string;
    }

    typedef mac-acl-name {
        type string {
            pattern '[a-zA-Z0-9]{1}([-a-zA-Z0-9_]{0,62})' {
            }
			length 1..63;
        }
    }
    
    typedef mac-acl-seq-id-t {
      type uint64 {
          range "0 .. 4294967290" {
          }
      }
    }

    typedef app-type {
        type uint16 {
           range "1536 .. 65535" {
           }
        }
    }

    typedef mac-resequence-starting-seq-id {
        type uint64 {
            range "0 .. 4294967290" {
            }
        }
    }

    typedef mac-resequence-increment-seq-id {
        type uint64 {
            range "1 .. 4294967290" {
            }
        }
    }

    grouping ext-access-list-rule {

        leaf action {
            type enumeration {
                enum permit {
                    value 1;
                }
                enum deny {
                    value 2;
                }
                enum hard-drop {
                    value 3;
                }
            }
        }

        leaf source {
            type union {
                type mac-address-type;
                    
                type enumeration {
                    enum any {
                        value 1;
                    }
                    enum host {
                        value 2;
                    }
                }
            }
            mandatory true;
        }

        leaf srchost {
            when "(../source='host')" {
            }
            type  mac-address-type;
        }
            
        leaf src-mac-addr-mask {
            when "((../source !='any') and (../source !='host'))" {
            }
            type src-dst-mac-address-mask-type;
        }

            
        leaf dst {
            type union {
                type mac-address-type;
                type enumeration {
                    enum any {
                        value 1;
                    }
                    enum host {
                        value 2;
                    }
                }
            }
            mandatory true;
        }

        leaf dsthost {
            when "(../dst='host')" {
            }
            type mac-address-type; 
        }

        leaf dst-mac-addr-mask {
            when "((../dst !='any') and (../dst !='host'))" {
            }
            type src-dst-mac-address-mask-type;
        }

        leaf ethertype {
            type union {
            type enumeration {
                enum arp {
                    value 2054;
                }
                enum fcoe {
                    value 35078;
                }
                enum ipv4 {
                    value 2048;
                }
            }
            type app-type;

            }
        }

		leaf vlan {
			//tailf:alt-name vlan;
			description "Vlan";
			type interface:vlan-type;
		}

        leaf count {
            type empty;
        }

        leaf log {
            type empty;
        }

    }

    grouping std-access-list-rule {
        leaf action {
            type enumeration {
                enum permit {
                    value 1;
                }
                enum deny {
                    value 2;
                }
                enum hard-drop {
                    value 3;
                }
            }
        }

        leaf source {
            type union {
                type mac-address-type;
                type enumeration {
                    enum any {
                        value 1;
                    }
                    enum host {
                        value 2;
                    }
                }
            }
            mandatory true;
        }

        leaf srchost {
            when "(../source='host')" {
            }
            type  mac-address-type;
        }

        leaf src-mac-addr-mask {
            when "((../source !='any') and (../source !='host'))" {
            }
            type src-dst-mac-address-mask-type;
        }
/*
        leaf vlan {
            //tailf:alt-name vlan;
            description "Vlan";
            type interface:vlan-type;
        }
*/		

        leaf count {
            type empty;
        }

        leaf log {
            type empty;
        }
    }

    grouping access-list-cmds {
        container mac {
            //tailf:cli-suppress-show-conf-path;
            container access-list {
                //standard ACL
                list standard {
                    key name;
                    leaf name {
                        type mac-acl-name; 
                    }
                    container hide-mac-acl-std {
	                    list seq {
	                        key seq-id;
	                        leaf seq-id {
	                            type uint64 {
	                                range "0 .. 4294967290" {
	                                }
	                            }
	                        }
	                        uses std-access-list-rule;
	                    }	                    
					}                    
                }
                
                //extended ACL                
                list extended {
                    key name;
                    leaf name {
                        type mac-acl-name;
                    }
                    
		            container hide-mac-acl-ext {
	                    list seq {
	                        key seq-id;
	                        leaf seq-id {
	                            type uint64 {
	                                range "0 .. 4294967290" {
	                                }
	                            }
	                        }
	                        uses ext-access-list-rule;
	                    }		                
		            }
                } // list extended
            } // container access-list
          } // container mac
    }// grouping 

    uses access-list-cmds;

    grouping l2_access_group {
        list access-group {

            key "mac-access-list mac-direction";

                leaf mac-access-list {
                type mac-acl-name;
            }

            leaf mac-direction {
                    
                type enumeration {
                    enum in {
                        value 1;
                    }
                    enum out {
                        value 2;
                    }
                }
            }
        }
    }

    augment "/interface:interface/interface:tengigabitethernet" {
        container mac {
            uses l2_access_group;
        }
    }

    augment "/interface:interface/interface:gigabitethernet" {
        container mac {
            uses l2_access_group;
        }
    }
    
    augment "/interface:interface/interface:fortygigabitethernet" {
        container mac {
            uses l2_access_group;
        }
    }

    augment "/interface:interface/interface:hundredgigabitethernet" {
        container mac {
            uses l2_access_group;
        }
    }


    augment "/interface:interface/interface:port-channel" {
        container mac {
            uses l2_access_group;
        }
    }
    augment "/interface:interface-vlan/interface:interface/interface:vlan" {
        container mac {
            uses l2_access_group;
        }
    }

    /* RPC Block */

    rpc get-mac-acl-for-intf {
        description
            "Function to query the MAC ACL applied on the
            interface(s).";

        input {
            uses interface:interface-name-info {
                description
                    "Name of the interface to query. Returns ACL details
                     of all the ports only for the Ingress direction, 
                     when name is not specified.";
            }
            
            leaf direction {
                type enumeration {
                    enum in {
                       value 1;
                       description
                           "Ingress direction.";
                    }
                    enum out {
                       value 2;
                       description 
                           "Egress direction.";
                    }                   
                    enum all {
                       value 3;
                       description 
                           "Ingress and Egress direction.";
                    }
                }
                mandatory false;
                description 
                   "To mention the direction in which ACLs are applied
                    on the interface. Returns ACL detail only for the 
                    Ingress direction, when direction is not specified";
            }
        }

        output {
            list interface {
                key "interface-type interface-name";
                uses interface:interface-name-info {
                    description "Interface name.";
                }
          
                list ingress-policy {
                    description
                        "Ingress policy details applied on this
                         interface.";
                    leaf policy-name {
                        type string;
                        description "MAC ACL policy name.";
                    }
                }
                
                list egress-policy {
                    description
                        "Egress policy details applied on this
                         interface.";
                    leaf policy-name {
                        type string;
                        description "MAC ACL policy name.";
                    }
                }                
            }
        }
    }
}
