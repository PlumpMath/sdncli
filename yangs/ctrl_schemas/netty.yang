module netty {
    yang-version 1;
    namespace "urn:opendaylight:params:xml:ns:yang:controller:netty";
    prefix "netty";

    import config { prefix config; revision-date 2013-04-05; }

    organization "Cisco Systems, Inc.";

    contact "Milos Fabian <milfabia@cisco.com>";

    description
        "This module contains the base YANG definitions for
         netty services.

        Copyright (c)2013 Cisco Systems, Inc. All rights reserved.;

        This program and the accompanying materials are made available
        under the terms of the Eclipse Public License v1.0 which
        accompanies this distribution, and is available at
        http://www.eclipse.org/legal/epl-v10.html";

    revision "2013-11-19" {
        description
            "Initial revision.";
    }

    identity netty-threadgroup {
        description
            "Configuration wrapper around netty's threadgroup";

        base "config:service-type";
        config:java-class "io.netty.channel.EventLoopGroup";
    }

    identity netty-event-executor {
        description
            "Configuration wrapper around netty's event executor";

        base "config:service-type";
        config:java-class "io.netty.util.concurrent.EventExecutor";
    }

    identity netty-timer {
        description
            "Configuration wrapper around netty's timer";

        base "config:service-type";
        config:java-class "io.netty.util.Timer";
    }

    identity channel-factory {
        description
            "Configuration wrapper around netty's channel factory";

        base "config:service-type";
        config:java-class "io.netty.bootstrap.ChannelFactory";
    }
}
