module packet-handler-impl {

  yang-version 1;
  namespace "urn:opendaylight:packet:packet-handler-impl";
  prefix "packet-handler-impl";

  import config { prefix config; revision-date 2013-04-05; }
  import opendaylight-md-sal-binding { prefix mdsal; revision-date 2013-10-28; }

  description
    "This module contains the base YANG definitions for
    packethandler-impl implementation.";

  revision 2014-05-28 {
    description "Initial module draft.";
  }

  // This is the definition of the service implementation as a module identity.
  identity packet-handler-impl {
    base config:module-type;

    // Specifies the prefix for generated java classes.
    config:java-name-prefix PacketHandler;
  }

  // Augments the 'configuration' choice node under modules/module.
  // We consume the three main services, RPCs, DataStore, and Notifications
  augment "/config:modules/config:module/config:configuration" {
    case packet-handler-impl {
      when "/config:modules/config:module/config:type = 'packet-handler-impl'";

      container notification-service {
        uses config:service-ref {
          refine type {
            mandatory true;
            config:required-identity mdsal:binding-notification-service;
          }
        }
      }
    }
  }
}
