module sal-port {
    namespace "urn:opendaylight:port:service";
    prefix port;

    import yang-ext {prefix ext; revision-date "2013-07-09";}
    import opendaylight-inventory {prefix inv;revision-date "2013-08-19";}
    import opendaylight-port-types {prefix port-type;revision-date "2013-09-25";}
    import flow-capable-transaction {prefix tr;}

    revision "2013-11-07" {
        description "Initial revision of port service";
    }        
    
    grouping node-port {
        uses "inv:node-context-ref";
        
        uses port-type:flow-port-status;
    }

    /** Base configuration structure **/
    grouping port-update {
        uses "inv:node-context-ref";

        container original-port {
            uses port-type:port-mod;
        }
        container updated-port {
            uses port-type:port-mod;
        }
    }

    rpc update-port {
        input {
            uses port-update;
            uses tr:transaction-aware;
        }
        output {
            uses tr:transaction-aware;
        }
    }
    
    notification port-updated {
        uses port-update;
        uses tr:transaction-aware;
    }
    
    notification port-removed {
        uses node-port;       
    }
}
