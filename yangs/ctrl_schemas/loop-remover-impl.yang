module loop-remover-impl {

  yang-version 1;
  namespace "urn:opendaylight:packet:loop-remover-impl";
  prefix "loop-remover-impl";

  import config { prefix config; revision-date 2013-04-05; }
  import opendaylight-md-sal-binding { prefix mdsal; revision-date 2013-10-28; }

  description
    "This module contains the base YANG definitions for
    loop-remover-impl implementation.";

  revision 2014-05-28 {
    description "Initial module draft.";
  }

  // This is the definition of the service implementation as a module identity.
  identity loop-remover-impl {
    base config:module-type;

    // Specifies the prefix for generated java classes.
    config:java-name-prefix LoopRemover;
  }

  // Augments the 'configuration' choice node under modules/module.
  augment "/config:modules/config:module/config:configuration" {
    case loop-remover-impl {
      when "/config:modules/config:module/config:type = 'loop-remover-impl'";

      leaf is-install-lldp-flow {
        type boolean;
      }
      leaf lldp-flow-table-id {
        type uint8;
      }
      leaf lldp-flow-priority {
        type uint16;
      }
      leaf lldp-flow-hard-timeout {
        type uint16;
      }
      leaf lldp-flow-idle-timeout {
        type uint16;
      }
      leaf graph-refresh-delay {
        type uint32;
      }
      leaf topology-id {
        type string;
      }
      container notification-service {
        uses config:service-ref {
          refine type {
            mandatory true;
            config:required-identity mdsal:binding-notification-service;
          }
        }
      }
      container data-broker {
        uses config:service-ref {
          refine type {
            mandatory false;
            config:required-identity mdsal:binding-async-data-broker;
          }
        }
      }
      container rpc-registry {
        uses config:service-ref {
          refine type {
            mandatory true;
            config:required-identity mdsal:binding-rpc-registry;
          }
        }
      }
    }
  }
}
