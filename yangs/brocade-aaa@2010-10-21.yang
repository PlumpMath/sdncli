/***********************************************************************
 * brocade-aaa.yang: Brocade AAA module data model
 *
 * November, 2010, Charanjith Reddy Kunduru
 *
 * Copyright (c) 2010 by Brocade Communications Systems, Inc.
 * All rights reserved.
 *
 **********************************************************************/

module brocade-aaa {
    namespace "urn:brocade.com:mgmt:brocade-aaa";
    prefix brcd-aaa;

    import tailf-common {
        prefix tailf;
    }

    import brocade-rbridge {
        prefix rbridge;
    }

    import brocade-common-def {
        prefix common-def;
    }
    organization
        "Brocade Communications Systems, Inc.";

    contact
        "Address :    120 Holger Way
                    San Jose, CA 95134
                    U.S.A
        Phone     :    +1-408-333-8000
        E-mail     :  support@brocade.com
        Website     :  www.brocade.com";

    description
        "Data Model for AAA CLIs";

    revision "2010-10-21" {
        description
            "Removed the max-elements attribute for list";
    }

    typedef auth-protocols {
        type enumeration {
            enum chap {
                value 0;
            }
            enum pap {
                value 1;
            }
            enum peap-mschap {
                value 2;
            }
        }
    }

    typedef rad-auth-protocols {
        type auth-protocols;
    }

    /* This has to be removed when peap is supported in tac+ */
    typedef tac-protocols {
        type enumeration {
            enum chap {
                value 0;
            }
            enum pap {
                value 1;
            }
        }
    }

    typedef tac-auth-protocols {
        type tac-protocols;
    }

    typedef tac-auth-port {
        type uint16 {
            range "1 .. 65535";
        }
    }

    typedef srcip_type {
        type enumeration {
            enum chassis-ip {
                value 1;
            }
            enum mm-ip {
                value 2;
            }
        }
    }

    typedef rad-auth-port {
        type uint16 {
            range "1 .. 65535";
        }
    }

    typedef ldap-auth-port {
        type uint16 {
            range "1 .. 65535";
        }
    }
    /* following are the datatypes for username list*/
    typedef user-passwd {
        type string {
            length "1..40";
        }
    }

    typedef username-enable {
        type boolean;
    }

    /* data types for rule */
    typedef action {
        type enumeration {
            enum accept;
            enum reject;
        }
    }

    typedef rule-action {
        type action;
    }

    typedef operation {
        type enumeration {
            enum read-only;
            enum read-write;
        }
    }

    typedef rule-operation {
        type operation;
    }

    typedef acc_srv_type {
        type enumeration {
            enum none {
                value 1;
            }
            enum tacacs+ {
                value 2;
            }
            // in future radius, ldap accounting may come here
        }
    }

    typedef ipv4-addr {
        type string {
            pattern '((0'
                +   '|(1[0-9]{0,2})'
                +   '|(2(([0-4][0-9]?)|(5[0-5]?)|([6-9]?)))'
                +   '|([3-9][0-9]?)'
                +  ')'
                + '\.){3}'
                + '(0'
                +  '|(1[0-9]{0,2})'
                +  '|(2(([0-4][0-9]?)|(5[0-5]?)|([6-9]?)))'
                +  '|([3-9][0-9]?))' {
            }
            }
    } 

    // Date datatype which accepts dates between 1902 and 2037. 	
    typedef date {
        type string {
             length "0 .. 10";
               pattern '((19(0[2-9]|[1-9][0-9])|20([012][0-9]|3[0-7]))-(0[1-9]|1[012])-(0[1-9]|[12][0-9]|3[01]))|never' {
                        error-message "Expiry date should be in the range 1902 and 2037, or 'never'(no expiry)";
               }
        }
    }

    typedef root_access_type {
        type enumeration {
            enum console {
                value 1;
            }
        }
    }

    container aaa-config {
    container aaa {
        container authentication {
            container login {
                leaf first {
                    type enumeration {
                        enum default {
                            value 0;
                        }
                        enum radius {
                            value 1;
                        }
                        enum tacacs+ {
                            value 2;
                        }
                        enum ldap {
                            value 3;
                        }
                        enum local {
                            value 4;
                        }
                    }
                }
                leaf second {
                    type enumeration {
                        enum local {
                            value 4;
                        }
                        enum local-auth-fallback {
                            value 5;
                        }
                    }
                }
            }
        }
        container accounting {
            container exec { 
                container defaultacc {
                    container start-stop {
                       leaf server-type {
                           type  acc_srv_type;
                       }
                    }
                }
            }
            container commands {
                container defaultacc {
                    container start-stop {
                       leaf server-type {
                           type  acc_srv_type;
                       }
                    }
                }
            }
        }
    }
    }

    list username {
        key "name";
        leaf name {
            type string {
                length "1 .. 40" {
                    error-message "User name length should be in the
                                   range 1-40";
                }
            }
        }
        leaf user-password {
            type user-passwd;
            mandatory true;
        }
        leaf encryption-level {
            type enumeration {
                enum 0 {
                    value 0;
                }
                enum 7 {
                    value 7;
                }
            }
        }
        leaf role {
            type string {
                length "4 .. 32" {
                    error-message "Role name length should be in the
                                   range 4-32";
                }
            }
            mandatory true;
        }
        leaf desc {
            type string {
                length "0 .. 64" {
                    error-message "Account description length should be
                                   in the range 0-64";
                }
            }
            default "";
        }
        leaf enable {
            type username-enable;
            default true;
        }
        leaf expire {
                type date {
                }
                default "never";
        }
    }

    container service {
        leaf password-encryption {
            type empty;
        }
    }

    container user {
        tailf:action unlock {
            input {
                leaf username {
                    type string {
                        length "1 .. 40" {
                            error-message "The existing user name length
                                           should be in the range 1-40";
                        }
                    }
                    mandatory true;
                }
                leaf rbridge-id {
                        mandatory false;
                        type common-def:rbridge-id-all-type;
                }
            }
            output {
                leaf Result {
                    type string {
                        length "0..max";
                    }
                }
            }
        }
    }

    container role {
        list name {
            key "name";
            leaf name {
                type string {
                    length "4 .. 32" {
                        error-message "Role name should be in the range
                                       4-32";
                    }
                }
            }
            leaf desc {
                type string {
                    length "0 .. 64" {
                        error-message "Role description should be in the
                                       range 0-64";
                    }
                }
                default "";
            }
        }
    }

    container radius-server {
        list host {
            key "hostname";
            leaf hostname {
                type string {
                    length "0..max";
                    pattern "\p{IsBasicLatin}{0,255}";
                }
            }
            leaf auth-port {
                type rad-auth-port;
                default 1812;
            }
            leaf protocol {
                type rad-auth-protocols;
                default chap;
            }
            leaf key {
                type string {
                    length "8 .. max" {
                    }
                }
            }
            leaf encryption-level {
                type enumeration {
                    enum 0 {
                        value 0;
                    }
                    enum 7 {
                        value 7;
                    }
                }
            }
            leaf retries {
                type uint32 {
                    range "0 .. 100" {
                        error-message "Retries must be in the
                                       range 0 - 100";
                    }
                }
                default 5;
            }
            leaf timeout {
                type uint32 {
                    range "1 .. 60" {
                        error-message "Timeout must be in the range
                                       1 - 60";
                    }
                }
                default 5;
            }
        }
    }

    container tacacs-server {
        list host {
            key "hostname";
            leaf hostname {
                type string {
                    length "0..max";
                    pattern "\p{IsBasicLatin}{0,255}";
                }
            }
            leaf port {
                type tac-auth-port;
                default 49;
            }
            leaf protocol {
                type tac-auth-protocols;
                default chap;
            }
            leaf key {
                type string {
                    length "1 .. max" {
                    }
                }
            }
            leaf encryption-level {
                type enumeration {
                    enum 0 {
                        value 0;
                    }
                    enum 7 {
                        value 7;
                    }
                }
            }
            leaf retries {
                type uint8 {
                    range "0 .. 100" {
                        error-message "Retries must be in the range
                                       0 - 100";
                    }
                }
                default 5;
            }
            leaf timeout {
                type uint8 {
                    range "1 .. 60" {
                        error-message "Timeout must be in the range
                                       1 - 60";
                    }
                }
                default 5;
            }
        }
        leaf tacacs-source-ip   {
            type srcip_type;
            default mm-ip;
        }
    }

    container ldap-server {
        list host {
            key "hostname";
            leaf hostname {
                type string {
                    length "1..max";
                    pattern "\p{IsBasicLatin}{0,255}";
                }
            }
            leaf port {
                type ldap-auth-port;
                default 389;
            }
            leaf retries {
                type uint8 {
                    range "0 .. 100" {
                        error-message "Retries must be in the range
                                       0 - 100";
                    }
                }
                default 5;
            }
            leaf timeout {
                type uint8 {
                    range "1 .. 60" {
                        error-message "Timeout must be in the range
                                       1 - 60";
                    }
                }
                default 5;
            }
            leaf basedn {
                type string {
                   length "1..255";
                }
                default "local";
            }
        }

        container maprole {
			list group {
				key "ad-group";
				leaf ad-group {
                	type string {
                   		length "1..max";
                	}
        		}

            	leaf switch-role {
                	type string {
                    	length "4 .. 32" {
                        	error-message "Role name should be in the range
                                       4-32";
                    	}
                	}
                    mandatory true;
            	}
			}
		}
	}

    container password-attributes {
        leaf min-length {
            type uint32 {
                range "8 .. 32" {
                    error-message "Password minimum length should be in
                                   the range 8-32";
                }
            }
            default 8;
        }
        leaf max-retry {
            type uint32 {
                range "0 .. 16" {
                    error-message "Maximum login retries value should
                                   be in the range 0-16";
                }
            }
            default 0;
        }
        container character-restriction {
            leaf upper {
                type uint32 {
                    range "0 .. 32" {
                        error-message "Minimum number of upper-case
                                 alphabets should be in the range 0-32";
                    }
                }
                default 0;
            }
            leaf lower {
                type uint32 {
                    range "0 .. 32" {
                        error-message "Minimum number of lower-case
                                 alphabets should be in the range 0-32";
                    }
                }
                default 0;
            }
            leaf numeric {
                type uint32 {
                    range "0 .. 32" {
                        error-message "Minimum number of numeric
                                characters should be in the range 0-32";
                    }
                }
                default 0;
            }
            leaf special-char {
                type uint32 {
                    range "0 .. 32" {
                        error-message "Minimum number of special
                                characters should be in the range 0-32";
                    }
                }
                default 0;
            }
        }
        leaf admin-lockout-enable {
            type empty; 
        }
    }

    container banner {
        leaf login {
            type string {
                length "0..2048" {
                }
            }
            default "";
        }
        leaf motd {
            type string {
                length "0..2048" {
                }
            }
            default "";
        }
        leaf incoming {
            type string {
                length "0..2048" {
                }
            }
            default "";
        }

    }

    grouping cmdstructure{
        container command {
             choice cmdlist {
                case container-cmds {
                     leaf  enumList{
                         type enumeration {
                            enum dot1x;
                            enum mac-address-table;
                            enum mac-rebalance;
                            enum cidrecov;
                            enum debug1;
                            enum lccli;
                            enum oscmd;
                            enum vlan;
                            enum qos;
                            enum mac;
                            enum sflow;
                            enum monitor;
                            enum system-monitor;
                            enum telnet;
                            enum ssh;
                            enum port-profile;
                            enum fcoe {
                            }
                            enum aaa {
                            }
                            enum radius-server {
                            }
                            enum tacacs-server {
                            }
                            enum ldap-server {
                            }
                            enum password-attributes {
                            }
                            enum username {
                            }
                            enum role {
                            }
                            enum banner {
                            }
                            enum rule {
                            }
                            enum alias-config {
                            }
                            enum snmp-server;
                            enum clock;
                            enum ntp;
                            enum fabric;
                            enum filter-change-update-delay;
                            enum license;
                            enum configure;
                            enum support;
                            enum logging;
                            enum firmware;
                            enum dir;
                            enum df;
                            enum prompt1;
                            enum prompt2;
                            enum delete;
                            enum rename;
                            enum diag;
                            enum vcs;
                            enum terminal;
                            enum cee-map;
                            enum interface {
                            }
                            enum ip;
                            enum ipv6;
                            enum management;
							enum nas;
                            enum protocol {
                            }
                            enum lacp;
                            enum switch-attributes;
                            enum vrf;
                            enum reload;
                            enum usb;
                            enum rmon;
                            enum fastboot;
                            enum unlock {
                            }
                            enum debug;
                            enum service {
                            }
							enum bp-rate-limit;
                            enum fcsp;
                            enum secpolicy;
                            enum ag;
							enum tnl;
							enum nsx-controller;
							enum nsx-controller-client;
                            enum no-operation;
                            enum vnetwork;
                            enum vCenter;
                        }
                    }
                }

                case interface-a {
                    container interface-int {
                        container interface-cont {
                            presence true;
                        }
                    }
                }

                case interface-b {
                    container interface-fcoe {
                        container interface {
                            container fcoe-cont {
                                presence true;
                            }
                        }
                    }
                }
                case interface-c {
                    container interface-te {
                        container interface {
                            container tengigabitethernet-cont {
                                presence true;
                            }
                        }
                    }
                }
                case interface-d {
                    container interface-fcoe-leaf {
                        container interface {
                            leaf fcoe-leaf {
                                type string;
                            }
                        }
                    }
                }

                case interface-e {
                    container interface-te-leaf {
                        container interface {
                            leaf tengigabitethernet-leaf {
                                type string;
                            }
                        }
                    }
                }

                case interface-f {
                    container interface-mgmt {
                        container interface {
                            container management-cont {
                                presence true;
                            }
                        }
                    }
                }
				case interface-g {
					container interface-ge {
						container interface {
						container gigabitethernet-cont {
								presence true;
							}
						}
					}
				}
				case interface-h {
					container interface-ge-leaf {
						container interface {
							leaf gigabitethernet-leaf {
								type string;
							}
						}
					}
				}
				case interface-i {
					container interface-pc {
						container interface {
							container port-channel-cont {
								presence true;
							}
						}
					}
				}
				case interface-j {
					container interface-pc-leaf {
						container interface {
							leaf port-channel-leaf {
								type string;
							}
						}
					}
				}
				case interface-k {
					container interface-vlan {
						container interface {
							container vlan-cont {
								presence true;
							}
						}
					}
				}
				case interface-l {
					container interface-vlan-leaf {
						container interface {
							leaf vlan-leaf {
								type string;
							}
						}
					}
				}
                case copy-a {
                    container copy-cp {
                        container copy-cont {
                            presence true;
                        }
                    }
                }

                case copy-b {
                    container copy-running {
                        container copy {
                            container running-config-cont {
                                presence true;
                            }
                        }
                    }
                }

                case copy-c {
                    container copy-support {
                        container copy {
                            container support-cp {
                                presence true;
                            }
                        }
                    }
                }

                case clear-a {
                    container clear-cl {
                        container clear-cont {
                            presence true;
                        }
                    }
                }

                case clear-b {
                    container clear-logging {
                        container clear {
                            container logging-cont {
                                presence true;
                            }
                        }
                    }
                }

                case clear-c {
                    container clear-support {
                        container clear {
                            container support-cl {
                                presence true;
                            }
                        }
                    }
                }

                case protocol-a {
                    container protocol-pr {
                        container  protocol-cont {
                            presence true;
                        }
                    }
                }

                case protocol-b {
                    container protocol-spanning {
                        container protocol {
                            container spanning-tree-cont {
                                presence true;
                            }
                        }
                    }
                }

                case protocol-c {
                    container protocol-lldp {
                        container  protocol{
                            container lldp-cont {
                                presence true;
                            }
                        }
                    }
                }
            }
        }
    }

    list rule {
        key index;
        leaf index {
            type uint32 {
                range "1 .. 512" {
                }
            }
        }
        leaf action {
            type rule-action;
        }
        leaf operation {
            type rule-operation;
        }
        leaf role {
            /*type leafref {
                path "/role/name/name";
            }*/
            type string {
                length "4 .. 32" {
                    error-message "Role name length should be in the
                                   range 4-32";
                }
            }
        }
        uses cmdstructure;
    }


    grouping root-group {
        container root {
            leaf enable {
                type empty;
            }
            leaf access {
                type root_access_type;
            }
        }
    }

    augment "/rbridge:rbridge-id" {
        uses root-group;
    }

    container root-sa {
       uses root-group;
    }

    typedef alias-name-type {
        type string {
            length "1..255" {
            }
        }
    }

    typedef alias-expansion-type {
        type string {
            length "1..1023" {
            }
        }
    }


    container alias-config {
        
        list alias {
            key name;
            leaf name {
                type string {
                    length "1..255" {
                        error-message "Alias name length should be
                                      in the range 1-255";
                    }
                }
            }
            leaf expansion {
                type string {
                    length "1..1023" {
                            error-message "Alias expansion length should be
                                    in the range 1-1023";
                    }
                }
                mandatory true;
            }
     } 

        list user { 
            key name;
            leaf name {
                type string {
                    length "1..40" {
                        error-message "User name length should be
                                       in the range 1-40";
                    }
                }
            }
            list alias {
                key name;
                leaf name {
                    type string {
                        length "1..255" {
                            error-message "Alias name length should be
                                           in the range 1-255";
                        }
                    }
                }
                leaf expansion {
                    type string {
                        length "1..1023" {
                            error-message "Alias expansion length should be
                                           in the range 1-1023";
                        }
                    }
                    mandatory true;
                }
            }
        }
    }

    augment "/common-def:clear" {
        container login {
            tailf:action sessions {
                description "Logout the user sessions in the switch";
                input {
                    leaf rbridge-id {
                        mandatory false;
                        type common-def:rbridge-id-all-type;
                    }
                }
                output {}
            }
        }
    }

    /*container rulespoint {
        tailf:action roleusers {
        }
        tailf:action rolerules {
        }
        tailf:action userrules {
        }
    }*/
}
