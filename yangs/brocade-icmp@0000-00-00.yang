/***********************************************************************
 * brocade-igmp : Brocade ICMP data model
 *
 * Copyright (c) 2014 by Brocade Communications Systems, Inc.
 * All rights reserved.
 *
 **********************************************************************/

module brocade-icmp {
    namespace "urn:brocade.com:mgmt:brocade-icmp";
    prefix icmp;

    import brocade-interface {
        prefix interface;
    }

    import brocade-rbridge {
        prefix rbridge;
    }

    import brocade-ip-config {
        prefix ip-config;
    }
    import brocade-ipv6-config {
        prefix ipv6-config;
    }
    import tailf-common {
        prefix "tailf";
    }



    grouping icmp-config {
        leaf echo-reply {
            type empty;
        }
        leaf rate-limiting  {
            type uint32 {
                range "1..4294967295" {
                }
            }
            default 1000;
        }
   
        leaf unreachable {
            type empty;
        }
        leaf redirect {
            type empty;
        }
    }

    grouping interface-icmp {
        container icmp  {

            uses icmp-config;
            leaf address-mask {
                type empty;
            }
         }
    }

    grouping interface-icmpv6 {
        container icmpv6  {

            uses icmp-config;
         }

    }


    augment "/rbridge:rbridge-id/interface:interface/interface:ve/ip-config:ip" {
        uses interface-icmp {
            refine icmp {
            }
        }
    }
    augment "/rbridge:rbridge-id/interface:interface/interface:ve/ipv6-config:ipv6" {
        uses interface-icmpv6 {
            refine icmpv6 {
            }
        }
    }
    augment "/interface:interface/interface:fortygigabitethernet/interface:ip" {
        uses interface-icmp {
            refine icmp {
            }
        }
    }

    augment "/interface:interface/interface:tengigabitethernet/interface:ip" {
        uses interface-icmp {
            refine icmp {
            }
        }
    }

    augment "/interface:interface/interface:gigabitethernet/interface:ip" {
        uses interface-icmp {
            refine icmp {
            }
        }
    }
    augment "/interface:interface/interface:hundredgigabitethernet/interface:ip" {
        uses interface-icmp {
            refine icmp {
            }
        }
    }
    augment "/interface:interface/interface:fortygigabitethernet/interface:ipv6" {
        uses interface-icmpv6 {
            refine icmpv6 {
            }
        }
    }

    augment "/interface:interface/interface:tengigabitethernet/interface:ipv6" {
        uses interface-icmpv6 {
            refine icmpv6 {
            }
        }
    }

    augment "/interface:interface/interface:gigabitethernet/interface:ipv6" {
        uses interface-icmpv6 {
            refine icmpv6 {
            }
        }
    }
    augment "/interface:interface/interface:hundredgigabitethernet/interface:ipv6" {
        uses interface-icmpv6 {
            refine icmpv6 {
            }
        }
    }
}
