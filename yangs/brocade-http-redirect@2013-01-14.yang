/***********************************************************************
 * brocade-http-redirect.yang: Brocade SNMP server Data Model
 *
 * January 2013,Balaji Chandrasekar
 *
 * Copyright (c) 2013 by Brocade Communications Systems, Inc.
 * All rights reserved.
 *
 **********************************************************************/
module brocade-http-redirect {
    namespace "urn:brocade.com:mgmt:brocade-http-redirect";
    prefix "http-server";

    import ietf-inet-types{
        prefix inet;
    }

    import tailf-common {
        prefix tailf;
    }

    organization
        "Brocade Communications Systems, Inc.";

    contact
        "Address :  120 Holger Way
                    San Jose, CA 95134
                    U.S.A
        Phone    :  +1-408-333-8000
        E-mail   :  support@brocade.com
        Website  :  www.brocade.com";

    description
        "Data Model for HTTP Server configuration";

    revision "2013-01-14" {
        description
            "Initial version";
    }


    rpc set-http-application-url {
        description "update http application url.";
        input {
            container config-http-app-url {
                leaf url {
                    type string {
                        length "0..512";
                    }
                    mandatory true;
                    description "HTTP application URL";
                }
                leaf op-type {
                    type uint32 {
                        range "0 .. 1";
                    }
                    mandatory true;
                    description
                        "Update URL - 1, unregister URL - 0";
                }
            }
        }

        output {
            leaf status-code {
                type int32 {
                    range "0 .. 10";
                }
                description
                    "URL updated successfully - 0,
                    Error not able to update configuration - 1,
                    Error not able to remove configuration - 2"; 
                mandatory true;
            }
            leaf status-string {
                type string {
                    length "0..255";
                    pattern "\p{IsBasicLatin}{0,255}";
                }
                description "Error in string format";
            }
        }
    }
}
