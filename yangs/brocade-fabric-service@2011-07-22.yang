/***********************************************************************
 * Fabric Related CLI Yang model
 *
 * Copyright (c) 2010 - 2014 by Brocade Communications Systems, Inc.
 * All rights reserved.
 **********************************************************************/

module brocade-fabric-service {
    namespace "urn:brocade.com:mgmt:brocade-fabric-service";
    prefix "fabric-service";

   import ietf-inet-types {
        prefix "inet";
    }

   import tailf-common {
        prefix tailf;
    }

    /* for user defined data-types */
    import brocade-common-def {
        prefix common-def;
    }

    import brocade-interface {
        prefix interface;
    }

    import brocade-rbridge {
        prefix rbridge;
    }

    organization
        "Brocade Communications Systems, Inc.";

    contact
        "Brocade Communications Systems, Inc.
         Postal: 130 Holger Way
                 San Jose, CA 95134
        U.S.A
         Tel: +1-408-333-8000
         E-mail: support@Brocade.co
         Web: www.brocade.com.";

    description
        "This management module gives Virtual Cluster Switching (VCS)
         FABRIC related information. VCS refers to the ability of
         a group of physical Ethernet switches, inter-connected
         in arbitrary fashion via the regular front-end
         data ports, to present themselves as one unified and
         transparent Ethernet switching service to the external network.
         The inter-connecting network that glues all these individual
         switches is refered as 'fabric', and the group of physical
         Ethernet switches in the fabric is refered to as 'cluster'.

         Glossary of the terms used:
         ---------------------------
         RBridge     - A Routing Bridge or RBridge is a network device
                       that implements the TRILL protocol, as defined
                       by the IETF.

         RBridge-ID  - RBridge-ID is the unique identifier of a node
                       in the fabric. It can take values from 1 - 239.

         ISL         - A inter switch link (ISL) is the link directly
                       connecting a fabric port of one switch to fabric
                       port of another switch. For an ISL to come up
                       both side of the link need to have
                       compatible configurations.

         Trunk       - Brocade trunk is a hardware based LAG (link
                       aggregation group) that is formed dynamically.
                       It is a technology that allows to combine up to
                       8 ISLs into a single logical trunk that provides
                       up to 80 Gigabits per second (Gbps) data
                       transfers.
                       Trunking uses a simple algorithm to optimally
                       distribute frames across a set of available paths
                       that link two adjacent switches. Such a set of
                       links is called trunking group.
                       In a trunk group one of the trunk ports is
                       used to set up all routing paths for the entire
                       trunk group. This port is called the 'trunk
                       master'.

         WWN         - World Wide Name (WWN) is a unique 64 bit
                       identifier that is assigned to a manufacturer
                       by the Institute of Electrical and Electronic
                       Engineers(IEEE) and hard-coded into a Fibre
                       Channel (FC) device.

         Principle   - In a fabric one switch is elected to manage
         Switch        RBridge-ID assignments within the fabric.
                       This switch is called the Principal Switch.
                       Each fabric has its own Principal Switch. If the
                       fabric configuration changes, a different switch
                       could become principal.
                       Note: In case of a single switch fabric, the same
                       switch acts as the Principal Switch.

         ECMP        - Equal cost multiple path (ECMP) is a routing
                       strategy where next-hop packet forwarding to a
                       single destination can occur over multiple
                       'best paths' which tie for top place in routing
                       metric calculations.

         BUM         - Broadcast, Unknown Unicast & Multicast (BUM)
                       traffic.

         FSPF        - Fabric Shortest Path First (FSPF) is a routing
                       protocol used in Fibre Channel networks.
                       It calculates the best path between switches,
                       establishes routes across the fabric and
                       calculates alternate routes in event of a
                       failure or topology change. FSPF guarantees
                       in-order delivery of frames, even if the
                       routing topology has changed during a failure,
                       by enforcing a 'hold down' time before a new
                       path is activated.

         Port ID(PID)- The Fibre Channel address ID in DDAAPP
                       hexadecimal format.

         VID         - VLAN identifier (VID).

         PISL        - Physical inter switch link (PISL).

         Note:
         The terms node and switch have been used interchangeably
         in this document. Both refer to the same.
       ";

    reference
        "ANSI INCITS xxx-xxxx, Fibre Channel - Switch Fabric - 5
        (FC-SW-5).
        ANSI INCITS 463-2010, Fibre Channel - Generic Services - 6
        (FC-GS-6).";

    revision 2011-07-22 {
        description "Initial version of this management module.";
    }

    /*** TYPE DEFINITIONS ***/
    typedef fabric-portid-type {
        type string {       
            length "6";         
            pattern "[0-9a-fA-F]*"; 
        }                       
        description
            "The definition to specify the Fibre Channel address
             (FCID). It is a 24-bit value unique within the address
             space of a Fabric. This definition is canonical
             representation of the address in hexadecimal format.";
    }

    typedef linkinfo-domain-reachable-type {
        type string {
            length "0..3";
            pattern 'Yes|No|yes|no';
        }
        description
            "Indicates whether the RBridge is reachable or not.
             Yes - Indicates RBridge is reachable
             No  - Indicates RBridge is not reachable.";
    }

    typedef interfacetype-type {
        type string {
            length "2";
            pattern 'Te|Fi';
        }
        description
            "Indicates the interface type.
             It can take the following values:
             Te - for 10G Ethernet ports
             Fi - for Fibre Channel ports.";
    }

    typedef linkinfo-trunked-type {
        type string {
            length "0..3";
            pattern 'Yes|No|yes|no';
        }
        description
            "Indicates whether the ISL is trunked or not.
             Yes - for trunked ISL port
             No  - for non trunked ISL port.";
    }

    typedef trunk-list-is-primary-type {
        type string {
            length "0..5";
            pattern 'True|False|true|false';
        }
        description
            "Indicates whether the port is Trunk master or not.";
    }

    typedef ethernet-port-type {
        type string {
            length "0..4";
            pattern 'Te|FCOE';
        }
        description
            "The port type of the RBridge.
             It can be either Te or FCOE.
             Te   - Stands for 10G Physical
                    Ethernet ports.
             FCOE - Stands for Fibre Channel over
                    Ethernet ports.";
    }

    typedef fibrechannel-port-type {
        type string {
            length "2";
            pattern 'Fi';
        }
        description
            "The  Fibre Channel port type of the RBridge.
             Fi - Stands for Fibre Channel ports.";
    }

    typedef porttype-type {
        type string {
            length "6";
            pattern 'E-Port|U-Port|G-Port|F-Port';
        }
        description
            "Fibre Channel port type of the RBridge.
	     This specifies the port type as 
	     E-Port:A Fabric Expansion Port that attaches
	     	    to another Interconnect_Port(E-Port or
		    B-Port) to create an Inter-Switch Link.
             F-Port:A port to which a non-loop N port is attached.
             G-Port:A generic fabric port which may function either
                    as an E_Port or an F_Port depending on the 
		    device connected on the otherside of the link.
             U-Port:An Unknown-port type when the port is unintialized
                    or non-operational.Such ports could be disabled
		    or without link.";
    }


    typedef hashswap-type {
        type uint32 {
            range "0..4294967295" {
            }
        }
    }

    /*** GROUPINGS ***/
    grouping rbridge-all {
        choice rbridge-id-or-all {
            case rbridge-id {
                leaf rbridge-id {
                    type common-def:rbridge-id-type;
                    description
                        "This specifies the RBridge-ID of the switch to
                         retrieve infomation from.";
                }
            }
            case all {
                leaf all {
                    type empty;
                    description
                        "This specifies that the information needs to
                         be retrieved from all RBridges in the
                         cluster.";
                }
            }
        }
    }

    grouping output-linkinfo {    
        list show-link-info {
            key linkinfo-rbridgeid;
            leaf linkinfo-rbridgeid {
                type common-def:rbridge-id-type;
                description
                    "The RBridge-ID of the node in the fabric.";
            }
            leaf linkinfo-domain-reachable {
                type linkinfo-domain-reachable-type;
                description
                    "Indicates whether the RBridge is reachable
                     or not.
                     Yes - Indicates RBridge is reachable
                     No  - Indicates RBridge is not reachable.";
            }
            leaf linkinfo-wwn {
                type common-def:wwn-type;
                description
                    "The WWN of the switch.";
            }
            leaf linkinfo-version {
                type uint32;
                description
                    "FSPF version.";
            }
            list linkinfo-isl {
                key linkinfo-isl-linknumber;
                leaf linkinfo-isl-linknumber {
                    type uint32;
                    description
                        "ISL number.";
                }
                leaf linkinfo-isllink-destdomain {
                    type common-def:rbridge-id-type;
                    description
                        "RBridge-ID of the remote/destination switch.";
                }
                leaf linkinfo-isllink-srcport {
                    type uint16;
                    description
                        "The source port index of the
                         RBridge.";
                }
                leaf linkinfo-isllink-srcport-type {
                    type interfacetype-type;
                    description
                        "Source port/interface type.
                         It can take the following values:
                         Te - for 10G Ethernet ports.
                         Fi - for Fibre Channel ports.";
                }
                leaf linkinfo-isllink-srcport-interface {
                    type interface:interface-type;
                    description
                        "Source port interface information
                         It is in the format
                         rbridge-id/slot/port.";
                }
                leaf linkinfo-isllink-destport {
                    type uint16;
                    description
                        "Remote/Destination port index of the ISL
                         connected to the source port.";
                }
                leaf linkinfo-isllink-destport-type {
                    type interfacetype-type;
                    description
                        "Remote/Destination port/interface type.
                         It can take the following values:
                         Te - for 10G Ethernet ports.
                         Fi - for Fibre Channel ports."; 
                }
                leaf linkinfo-isllink-destport-interface {
                    type interface:interface-type;
                    description 
                        "Remote/Destination port interface information
                         It is in the format
                         rbridge-id/slot/port.";                  
                }
                leaf linkinfo-isl-linkcost {
                    type uint32;
                    description
                        "The cost of the link to reach the
                         destination. This is a dimensionless
                         positive number. Every ISL has a
                         default cost that is inversely
                         proportional to its bandwidth.";
                }
                leaf linkinfo-isllink-costcount {
                    type uint32;
                    description
                        "Cost count of the link.";
                }
                leaf linkinfo-isllink-type {
                    type uint32;
                    description
                        "Provides the type of the link.
                         It can be point to point or
                         virtual links or PISL  or
                         point to point ethernet.
                         This parameter is set to
                         '1' for point to point,
                         '2' for virtual links,
                         '3' for PISL and 
                         '4' for point to point ethernet.";
                }
                leaf linkinfo-trunked {
                    type linkinfo-trunked-type;
                    description
                        "Indicates whether the ISL is trunked or not.
                         Yes - for trunked ISL port
                         No  - for non trunked ISL port.";
                }
            }
        }
    }

    /*** NODE SPECIFIC COMMANDS GROUPING ***/
    grouping mcast-priority {
        container route {
            description
                "Function to configure routing related information
                 such as multicast priority.";
            container mcast {
                description
                    "This function is to configure multicast routing
                     related information for a switch.";
                leaf priority {
                    description
                        "This specifies the multicast priority
                         to be configured for the switch.
                         By default the multicast priority is 1.";
                    type common-def:mcast-priority-type;
                    default 1;
                }
            }
        }
    }

    grouping ecmp-loadbalance {
        container ecmp {
            description
                "This function allows to configure ECMP
                 related parameters.";
            leaf ecmp-load-balance {
                description
                    "This function allows to configure load
                     balancing parameters that are used in
                     ECMP hashing.";
                type enumeration {
                    enum dst-mac-vid {
                        value 1;
                        description
                            "Destination MAC address and
                             VLAN ID(VID) based load balancing.";
                    }
                    enum src-mac-vid {
                        value 2;
                        description
                            "Source MAC address and VLAN ID (VID)
                             based load balancing.";
                    }
                    enum src-dst-mac-vid {
                        value 3;
                        description
                            "Source and Destination MAC address
                             and VLAN ID (VID) based load balancing.";
                    }
                    enum src-dst-ip {
                        value 4;
                        description
                            "Source and Destination IP address
                             based load balancing.";
                    }
                    enum src-dst-ip-mac-vid {
                        value 5;
                        description
                            "Source and Destination IP and MAC
                             address and VID based load balancing.";
                    }
                    enum src-dst-ip-port {
                        value 6;
                        description
                            "Source and Destination IP and
                             TCP/UDP port based load balancing.";
                    }
                    enum src-dst-ip-mac-vid-port {
                        value 7;
                        description
                            "Source and Destination IP, MAC address,
                             VID and TCP/UDP port based load
                             balancing (default)";
                    }
                }
                default src-dst-ip-mac-vid-port;
            }
            leaf load-balance-hash-swap {
                description
                    "This command is used to configure how to swap
                     the input fields before feeding them to the
                     hash function.";
				type hashswap-type;
				default 0;
            }
        }
    }

    grouping vlag-loadbalance {
        list port-channel {

            key "po-id";

            leaf po-id {
                type interface:portchannel-type;
            }
            leaf vlag-load-balance {
                type enumeration {
                    enum dst-mac-vid {
                        value 1;
                    }
                    enum src-mac-vid {
                        value 2;
                    }
                    enum src-dst-mac-vid {
                        value 3;
                    }
                    enum src-dst-ip {
                        value 4;
                    }
                    enum src-dst-ip-mac-vid {
                        value 5;
                    }
                    enum src-dst-ip-port {
                        value 6;
                    }
                    enum src-dst-ip-mac-vid-port {
                        value 7;
                    }
                }
                default src-dst-ip-mac-vid-port;
            }
        }
    }


    /*** FABRIC - SHOW CONTAINER ***/
    augment "/common-def:show" {
        container fabric {
            description
                "This function provides fabric related information.
                 This includes information about the various RBridges
                 in the fabric, ISL connectivity information, fabric
                 topology, routing info, multicast tree details, etc.
                 This information is applicable/available only when
                 the VCS mode is enabled. In VCS disabled mode
                 (standalone mode) fabric does not exist.";

            tailf:action all {
                description
                    "This function provides the entire VCS fabric
                     membership information.";
                input {
                }
                output {
                    list fabric-showall-cluster {
                        key fabric-showall-rbridge-id;
                        leaf fabric-showall-rbridge-id {
                            type common-def:rbridge-id-type;
                            description
                                "Provides the RBridge-ID of the
                                 switch in the fabric.";
                        }
                        leaf fabric-showall-wwn {
                            type common-def:wwn-type;
                            description
                                "WWN of the node.";
                        }
                        leaf fabric-showall-ipaddress {
                            /*type common-def:ipv4-prefix-mask;*/
                            type inet:ipv4-address; 
                            description
                                "IPv4 address of the node.";
                        }
                        leaf fabric-showall-name {
                            type string;
                            description
                                "Name of the switch.";
                        }
                        leaf fabric-showall-version {
                            type string;
                            description
                                "Firmware version of the node.";
                        }
                        leaf fabric-showall-swbd-number {
                            type int32;
                            description
                                "Model number of the switch.";
                        }
                        leaf fabric-is-principalswitch {
                            type boolean;
                            description
                                "Node is a fabric principal switch
                                 when this parameter is set to TRUE.";
                        }
                        leaf fabric-showall-ipv6address {
                            /*type common-def:inet-address-type; */
                             type inet:ipv6-address; 
                            description
                                "IPv6 address of the node.";
                        }
                    }
                }
            } /* fabricshow */

            tailf:action isl {
                description
                    "This function provides the ISL information
                     of the switch.";
                input {
                    uses rbridge-all;
                }
            } /* islshow */

            tailf:action islports {
                description
                    "This function provides detailed information
                     of all ISL ports on the switch.";
                input {
                    uses rbridge-all;
                }
            } /* switchshow */

            tailf:action trunk {
                description
                    "This function provides the ISL trunk
                     information.";
                input {
                    uses rbridge-all;
                }
                output {
                    list show-trunk-list {
                        list trunk-list-groups {
                            leaf trunk-list-group {
                                type uint32;
                                description
                                    "Provides the trunk group number
                                     the interface belongs to.
                                     Trunk members of a trunk group
                                     have the same group number.";
                            }
                            list trunk-list-member {
                                leaf trunk-list-src-port {
                                    type uint32;
                                    description
                                        "Source port index of
                                         the trunk member.";
                                }
                                leaf trunk-list-interface-type {
                                    type interfacetype-type;
                                    description
                                        "Interface type.
                                         It can take the following
                                         values:
                                         Te - for 10G Ethernet interface
                                         Fi - for Fibre Channel
                                              interface.";
                                }
                                leaf trunk-list-src-interface {
                                    type interface:interface-type;
                                    description
                                        "Source port interface info
                                         It is in the format
                                         rbridge-id/slot/port.";
                                }
                                leaf trunk-list-nbr-rbridge-id {
                                    type uint32;
                                    description
                                        "RBbridge id of the neighboring
                                         switch that connects to this
                                         trunk member port.";
                                }
                                leaf trunk-list-nbr-port {
                                    type uint32;
                                    description
                                        "Neighbor port index of the
                                         trunk member.";
                                }
                                leaf trunk-list-nbr-wwn {
                                    type common-def:wwn-type;
                                    description
                                        "WWN of the neighboring
                                         switch that connects to this
                                         trunk member port.";
                                }
                                leaf trunk-list-is-primary {
                                    type trunk-list-is-primary-type;
                                    description
                                        "This parameter is set to True
                                         for trunk master.";
                                }
                            }
                        }
                    }
                }
            } /* trunkshow */

            container route {
                description
                    "Provides routing related information.
                     This includes multicast tree details, multicast
                     priority, topology information, link cost etc.";

                tailf:action multicast {
                    description
                        "This function provides multicast routing
                         information. This includes the multicast tree
                         its root, priority, etc.
                         A multicast tree is a loop free tree
                         consisting of all nodes in cluster.
                         Usually, the node with lowest RBridge-ID
                         becomes the root. BUM traffic is always
                         forwarded on the multicast tree
                         (regardless of VLAN ID).";
                    input {
                        uses rbridge-all;
                    }
                } /* multicastshow */

                tailf:action topology {
                    description
                        "Topology is the  the layout pattern of
                         interconnections of the various elements
                         (links, nodes, etc.). This function provides
                         fabric topology infomation as seen by a
                         VCS node. This includes the number of
                         currently active paths to the destination,
                         maximum number of hops to reach destination,
                         cost of reaching destination etc.";
                    input {
                        leaf dest-rbridge-id {
                            type common-def:rbridge-id-type;
                            description
                                "This specifies the RBridge-ID of
                                 the destination switch.";
                        }
                        leaf src-rbridge-id {
                            type common-def:rbridge-id-type;
                            description
                                "This specifies the RBridge-ID of the
                                 source switch.";
                        }
                    }
                } /* topologyshow */

                tailf:action pathinfo {
                    description
                        "Provides routing information and states along
                         a path covering multiple switches.";
                    input {
                    }
                } /* pathinfo */

                tailf:action linkinfo {
                    description
                        "Provides details of all the links connected in
                         the fabric. This information is given in groups
                         for all the RBridges in the fabric.";
                    input {
                    }       
                    output {
                        uses output-linkinfo;
                    }
                } /*linkinfo */

                tailf:action neighbor-state {
                    description
                        "Provides the FSPF link state information of a
                         node. A FULL state indicates FSPF link state
                         database exchange is complete and that link
                         can be used while making routing decisions.";
                    input {
                        uses rbridge-all;
                    }
                } /* nbrstateshow */
            }
        }
    } /* end of show */


    /*** Custom RPC's ***/
    rpc show-linkinfo {
         description
             "Provides details of all the links connected in
              the fabric. This information is given in groups
              for all the RBridges in the fabric.";
            input {
                leaf all {
                    type empty;
                }
            }
            output {
                uses output-linkinfo;
            }
    }

    rpc show-portindex-interface-info {
        description
            "Provides the details of 10G Ethernet and fibrechannel
             over ethernet ports. It consists of port index of the
             RBridge, port type (Te or FCOE) and port interface.
             Port interface is in the format
             rbridge-id/slot/port for Te ports and
             vlan-id/rbridge-id/port for FCOE ports.";
            input {
                leaf all {
                    type empty;
                }
            }
             output {
                list show-portindex-interface {
                    key portsgroup-rbridgeid;
                    leaf portsgroup-rbridgeid {
                        type common-def:rbridge-id-type;
                    description
                        "The RBridge-ID of the switch
                         in the cluster.";
                }
                list show-portindex {
                    key port-index;
                    leaf port-index {
                        type uint32;
                        description
                            "The port index of the RBridge.";
                    }
                    leaf port-type {
                        type ethernet-port-type;
                        description
                            "The port type of the RBridge.
                             It can be either Te or FCOE.
                             Te   - Stands for 10G Physical
                                    Ethernet ports.
                             FCOE - Stands for Fibre Channel over
                                    Ethernet ports.";
                    }
                    leaf port-interface {
                        type interface:interface-type;
                        description
                            "Port index interface representation.
                             It is represented in the format
                             Te   - rbridge-id/slot/port
                             FCOE - vlan-id/rbridge-id/port.";
                    }
                }
            }
        }
    }

     rpc show-fibrechannel-interface-info {
        description
            "Provides all detailed information of fibrechannel ports
             in the RBridge. It consists of port index of the RBridge,
             port type (E-port/F-port/G-port/U-port), port interface, port
             address, port WWN, remote port WWN, remote node WWN,
             port state, port status, port status message, port health,
             trunk details, licence details etc.";
             input {
                 leaf all {
                     type empty;
                 }
             }
             output {
                list show-fibrechannel-interface {
                    key portsgroup-rbridgeid;
                    leaf portsgroup-rbridgeid {
                        type common-def:rbridge-id-type;
                    description
                        "The RBridge ID of the switch.";
                    }
                    list show-fibrechannel-info {
                        key port-index;
                        leaf port-interface {
                            type interface:interface-type;
                        description
                            "The Fibre Channel port interface.
                             It is represented in the format
                             rbridge-id/slot/port.";
                    }
                    leaf port-index {
                        type uint32;
                        description
                            "The Fibre Channel port index of the
                             RBridge.";
                    }
                    leaf port-type {
                         type porttype-type;
                        }
                        leaf port-wwn {
                            type common-def:wwn-type;
                        description
                            "Local Fibre Channel port WWN.";
                        }
                        leaf remote-port-wwn {
                            type common-def:wwn-type;
                        description
                            "WWN of the remote port that connects
                             to this Fibre Channel port.";
                        }
                        leaf remote-node-wwn {
                            type common-def:wwn-type;
                        description
                            "WWN of the remote switch that connects
                             to this Fibre Channel port.";
                        }
                        leaf port-state {
                            type string;
                        description
                            "This specifies the Fibre Channel port
                             State. The state can be 
                             Online or Offline.";
                        }
                        leaf port-status {
                            type string;
                        description
                            "Provides the Fibre Channel port
                             status. The Fibre Channel port status
                             can be Online, No Module, No Light,
                             In Sync, No Sync etc.";
                        }
                        leaf port-status-message {
                            type string;
                        description
                            "Provides the Fibre Channel port status
                             messages. It consists of messages like
                             down stream, trunk port, trunk
                             master etc.";
                        }
                        leaf port-health {
                           type string;
                        description
                            "Provides the Fibre Channel port health
                             information. It consists of information
                             like fabric watch licence details, etc.";
                        }
                        leaf port-trunked {
                           type boolean;
                        description
                            "Provides the Fibre Channel port trunk
                             information. This parameter is set to
                             'true' for trunked ports and 'false' for
                             non trunked ports.";
                        }
                        leaf port-trunk-master {
                            type uint32;
                        description
                            "Provides the Fibre Channel port trunk
                             master information. This parameter value
                             is set to '1' for trunk master and
                             '0' for slave ports.";
                        }
                        leaf port-actual-distance {
                            type uint32;
                        description
                            "Provides the Fibre Channel port Actual
                             Distance Information.";
                        }
                        leaf port-desired-credit {
                            type uint32;
                        description
                            "Provides the Fibre Channel port Desired
                             Credit Information.";
                        }
                        leaf port-buffer-allocated {
                            type uint32;
                        description
                            "Provides the Fibre Channel port Buffer
                             Allocation.";
                        }
                        leaf port-licensed {
                            type boolean;
                        description
                            "Indicates if the port is
                             licensed or not. This is set to 'true'
                             for licenced ports and 'false' for
                             non licenced ports.";
                        }
                        leaf port-address {
                            type fabric-portid-type;
                        description
                            "Fibre Channel address (24 bit
                             address PID).
                             Uses hexadecimal format.";
                        }
                        leaf port-fec {
                            type string;
                        description
                            "Provide port FEC operational status of a port.
                               Active - When FEC enabled and operational on a port. 
                               Inactive - When FEC is not operational on a port. 
                               Not Supported - When the platform doesn't support FEC feature.";
                        }
                }
            }
        }
    }


    /*** FABRIC - CONFIGURE CONTAINER ***/
    container fabric {
        description
            "This function is used to configure fabric
             parameters such as multicast priority.";

        container route {
            description
                "Function to configure routing related information
                 such as multicast priority.";

            status deprecated;
            container mcast {
                description
                    "This function is to configure multicast routing
                     related information like multicast priority for
                     a node. Node with highest multicast priority
                     (and/or lowest RBridge-ID) becomes the root of
                     the multicast tree.";
                list rbridge-id {
                    description
                        "This function is to configure multicast
                         priority for a given RBridge.";
                    key rbridge-id;
                    leaf rbridge-id {
                        type common-def:rbridge-id-type;
                        description
                            "This specifies the RBridge-ID of switch
                             for which the multicast priority is to
                             be configured.";
                    }
                    leaf priority {
                        type common-def:mcast-priority-type;
                        default 1;
                        description
                            "This specifies the multicast priority
                             to be configured for the switch. A higher
                             value indicates a higher priority.
                             By default the multicast priority is 1.";
                    }
                }
            }
        }
    }

    /*** FABRIC - NODE SPECIFIC CONFIGURATION COMMAND CONTAINER ***/
    augment "/rbridge:rbridge-id" {
        container fabric {
            description
                "This function is used to configure fabric
                 parameters such as ECMP load balancing parameters
                 and multicast priority.";

            /* ecmp load-balance */
            uses ecmp-loadbalance;

            /* mcast priority */
            uses mcast-priority;

            /* vlag load-balance */
            uses vlag-loadbalance;
        }
    }

} /* end of fabric-service submodule */
