/***********************************************************************
* brocade-threshold-monitor.yang-: Brocade System Monitor Data Model
*
* November 2011,Ramya Rangarajan
*
* Copyright (c) 2011 by Brocade Communications Systems, Inc.
* All rights reserved.
*
**********************************************************************/

module brocade-threshold-monitor {
	namespace "urn:brocade.com:mgmt:brocade-threshold-monitor";
	prefix "threshold-monitor";

	import tailf-common {
        	prefix tailf;
	}

    import brocade-rbridge { 
        prefix rbridge;
    }

	organization
		"Brocade Communications Systems, Inc.";

	contact
		"Address :  120 Holger Way
			    San Jose, CA 95134
			    U.S.A
		Phone    :  +1-408-333-8000
		E-mail   :  support@brocade.com
		Website  :  www.brocade.com";

	description
		"Data Model for Brocade's System Monitor configuration CLIs";

	revision "2011-11-24" {
		description
			"Initial modelling of Yang";
	}

	typedef supported-actions {
		type bits {
			bit none { position 0; }
			bit all { position 1; }
			bit email { position 2; }
			bit raslog { position 3; }
		}
	}
	typedef int-supported-actions {
		type bits {
			bit none { position 0; }
			bit all { position 1; }
			bit email { position 2; }
			bit raslog { position 3; }
			bit fence {position 4;}
		}
	}

 	typedef supported-monitoring {
	    type enumeration {
	        enum custom-monitoring {
	    	}
		enum default-monitoring {
		}
	    }
	}
	typedef supported-config {
		type string {
			//pattern 'custom';
		}
	}
	typedef supported-timebase {
		type enumeration {
			enum none {
			    value 0; 
			}
			enum minute {
			     value  2; 
			}
			enum hour {
			     value 3; 
			}
			enum day {
			     value 4;
			}
		}
	}

	grouping threshold-monitor-group {  
	container threshold-monitor {
		container sfp {
			leaf apply{
					type supported-config;
			}
			leaf pause {
				//tailf:cli-show-no;
				type empty;
			}
			list policy {
			//	tailf:cli-drop-node-name;
				key policy_name;
				leaf policy_name {
					type string {
						//pattern 'custom';
					}
				}
				list area {
					key "type area_value";
					leaf type {
						type enumeration {
							enum 1GSR {
								 value 0;
							}
							enum 1GLR {
								 value 1;
							}
							enum 10GSR {
								value 2;
							}
							enum 10GLR {
								value 3;
							}
							enum 10GUSR {
								value 4;
							}
							enum QSFP {
								value 5;
							}
							/*enum 40GLR {
								value 6;
							}*/
							enum 100GSR {
								value 7;
							}
							/*enum 100GLR {
								value 8;
							}*/
						}
					}
					leaf area_value {
						type enumeration {
							enum Temperature {
								value 0;
							}
							enum RXP {
								value 1;
							}
							enum TXP {
								value 2;
							}
							enum Current {
								value 3;
							}
							enum Voltage {
								value 4;
							}
						}
					}
					container threshold {
						leaf high-threshold {
							type int32;
						}
						leaf low-threshold {
							type int32;
						}
						leaf buffer {
							type int32;
						}
					}
					container alert {
						container above {
							leaf above-highthresh-action {
								type supported-actions;
							}
						}
						container below {
							leaf below-highthresh-action {
								type supported-actions;
							}
							leaf below-lowthresh-action {
								type supported-actions;
							}
						}
					}
				}
			}
		}
		container security {
			leaf apply {
				type supported-config;
			}
			leaf pause {
				//tailf:cli-show-no;
				type empty;
			}
			list policy {
				//tailf:callpoint securitymonitoring;
				key sec_policy_name;
                leaf sec_policy_name {
                	type string {
                    }
				}
              	list area {
					key "sec_area_value";
					leaf sec_area_value {
						type enumeration {
							enum telnet-violation {
								value 0;
							}
							enum login-violation {
								value 11;
							}
						}
					}	
					leaf timebase {
						type supported-timebase;
					}
					container threshold {
						leaf sec-high-threshold {
							type int32;
						}
						leaf sec-low-threshold {
							type int32;
						}
						leaf sec-buffer {
							type int32;
						}
					}
					container alert {
						container above {
							leaf sec-above-highthresh-action {
								type supported-actions;
							}
						}
						container below {
							leaf sec-below-highthresh-action {
								type supported-actions;
							}
							leaf sec-below-lowthresh-action {
								type supported-actions;
							}
						}
					}
				}
			}
		}
		container Cpu {
			leaf poll {
				type uint32 {
					range "10 .. 3600" {
						error-message "Polling interval must be in range
							10 - 3600";
					}
				}
				default 120;
			}
			leaf retry {
				type uint32 {
					range "1 .. 100" {
						error-message "Retries must be in range 1 - 100";
					}
				}
				default 3;
			}
			leaf limit {
				type uint32 {
					range "0 .. 80" {
						error-message "Usage limit must be in range 0 - 80";
					}
				}
				default 75;
			}

			leaf actions {
				type enumeration {
					enum none {
						value 1;
					}

					enum raslog {
						value 2;
					}
			/*	
					enum snmp {
						value 3;
					}
		
					enum all {
						value 4;
					}
			*/
				}
				default none;
			}
		}
		container Memory {
			leaf poll {
				type uint32 {
					range "10 .. 3600" {
						error-message "Polling interval must be in range
							10 - 3600";
					}
				}
				default 120;
			}

			leaf retry {
				type uint32 {
					range "1 .. 100" {
						error-message "Retries must be in range 1 - 100";
					}
				}
				default 3;
			}

			leaf limit {
				type uint32 {
					range "0 .. 80" {
						error-message "Memory usage limit must be in range 0 - 80";
					}
				}
				default 60;
			}

			leaf high-limit {
				type uint32 {
					range "0 .. 80" {
						error-message "Memory usage high-limit must be in range 0 - 80";
					}
				}
				default 70;
			}
			leaf low-limit {
				type uint32 {
					range "0 .. 80" {
						error-message "Memory usage low-limit must be in range 0 - 80";
					}
				}
				default 40;
			}

			leaf actions {
				type enumeration {
					enum none {
						value 1;
					}

					enum raslog {
						value 2;
					}
			/*	
					enum snmp {
						value 3;
					}
		
					enum all {
						value 4;
					}
			*/
				}
				default none;	
			}
		}
		container interface {
			leaf apply {
				type supported-config;
			}
			leaf pause {
				type empty;
			}
			list policy {
				//tailf:cli-drop-node-name;
				key policy_name;
				leaf policy_name {
					type string {
					}
				}
				list area {
					key "type area_value";
					leaf type {
						type enumeration {
							enum Ethernet {
								 value 0;
							}
						}
					}
					leaf area_value {
						type enumeration {
							enum MissingTerminationCharacter {
								value 0;
							}
							enum CRCAlignErrors {
								value 1;
							}
							enum SymbolErrors {
								value 2;
							}
							enum IFG {
								value 3;
							}
						}
					}
					container threshold {
						leaf timebase_value {
							type supported-timebase;
						}
						leaf high-threshold {
							type int32;
						}
						leaf low-threshold {
							type int32;
						}
						leaf buffer {
							type int32;
						}
					}
					container alert {
						container above {
							leaf above-highthresh-action {
								type int-supported-actions;
							}
							leaf above-lowthresh-action {
								type supported-actions;
							}
						}
						container below {
							leaf below-highthresh-action {
								type supported-actions;
							}
							leaf below-lowthresh-action {
								type supported-actions;
							}
						}
					}
				}
			}
		}
	}
}
	augment "/rbridge:rbridge-id" {
			uses threshold-monitor-group;
	}

	container threshold-monitor-hidden {
		uses threshold-monitor-group;
	}
}
