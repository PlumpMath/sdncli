/***********************************************************************
 * brocade-common-def.yang: Brocade common YANG derived data types.
 *
 * Feb 2010, Sanjeev C Joshi
 *
 * Copyright (c) 2010 by Brocade Communications Systems, Inc.
 * All rights reserved.
 *
 **********************************************************************/

module brocade-common-def {
    namespace "urn:brocade.com:mgmt:brocade-common-def";
    prefix "common-def";

    
    import ietf-inet-types  { prefix "inet"; }
    import tailf-common {
        prefix tailf;
    }
    
    organization
        "Brocade Communications Systems, Inc.";
    
    contact           
        "Brocade Communications Systems, Inc.
         Postal: 1745 Technology Drive,
                 San Jose, CA 95110 
                  U.S.A
         Tel: +1-408-392-6061
         E-mail: support@Brocade.com 
         web: www.brocade.com.";

    description       
        "This management module contains collection of most commonly 
        used derived YANG data types within the 'Broacde' name-space.";
        
    revision "2010-02-22" {
        description     
            "Initial version of this management module.";
    }
    
	typedef lc-number-type {
		type uint16 {
       		range "0..65535";
     	}
		description "The lc-number-type represents a 16-bit line card number in the managed entity.";
	}

    /* inspired by INET-ADDRESS-MIB */
    typedef inet-address-type {
        type enumeration {
            enum unknown { tailf:code-name inet-address-type-unknown; value 0; }
            enum ipv4    { tailf:code-name inet-address-type-ipv4; value 1; }
            enum ipv6    { tailf:code-name inet-address-type-ipv6; value 2; }
            enum ipv4z   { tailf:code-name inet-address-type-ipv4z; value 3; }
            enum ipv6z   { tailf:code-name inet-address-type-ipv6z; value 4; }
            enum dns     { tailf:code-name inet-address-type-dns; value 16; }
        }
    }

    grouping inet-address {
        description
            "A generic address group. The value of an 'address'
            must always be consistent with the value of the 
            associated 'type' leaf.";
            
        leaf address-type {
            type inet-address-type;
        }
        
        leaf address {
            type inet:host;
        }
    } 
    
    typedef ipv4-mask {
        type string {
            pattern '(([0]|25[0-5])\.){3}' + '([0]|25[0-5])';
        }
    }

    typedef ipv4-prefix-mask {
     type string {
       pattern
          '(([1-9]|[1-9][0-9]|1[0-9][0-9]|2[0-4][0-9]|25[0-5])\.)'
        + '(([0-9]|[1-9][0-9]|1[0-9][0-9]|2[0-4][0-9]|25[0-5])\.){2}'
        +  '([0-9]|[1-9][0-9]|1[0-9][0-9]|2[0-4][0-9]|25[0-5])'
        + '/(([1-9])|([1-2][0-9])|(3[0-1]))'
        {
            error-message
                "Invalid IPv4 Address/Mask format";
        }
     }
    }

    typedef vrf-name {
        type string {
            pattern '((([a-zA-Z0-9_]([a-zA-Z0-9\-_]){0,61})?[a-zA-Z0-9]\.)*'
                    +  '([a-zA-Z0-9_]([a-zA-Z0-9\-_]){0,61})?[a-zA-Z0-9]\.?)'
                    +  '|\.';
            length "1..32";
        }
        reference
            "L. Andersson, 'Provider Provisioned Virtual Private 
            Network (VPN) Terminology', RFC 4026, March 2005.";
    }

    typedef vrf-custom-type {
        type union {
            type vrf-name {
            }
            type enumeration {
                enum  mgmt-vrf {
                }
                enum  default-vrf {
                }
                enum  all {
                }
            }
        }
    }

    typedef vrf-id {
        type uint32 {
            range "0..65535" {
            }
        }
        description
            "VRF id, which is the system assigned unique id for
             each VRF";
    }

    /* inspired by IANA-RTPROTO-MIB */
    
    typedef ip-route-protocol {
        type enumeration {
            enum other      { value 1; }
            enum local      { value 2; }
            enum netmgmt    { value 3; }
            enum icmp       { value 4; }
            enum egp        { value 5; }
            enum ggp        { value 6; }
            enum hello      { value 7; }
            enum rip        { value 8; }
            enum isIs       { value 9; }
            enum esIs       { value 10; }
            enum ciscoIgrp  { value 11; }
            enum bbnSpfIgp  { value 12; }
            enum ospf       { value 13; }
            enum bgp        { value 14; }
            enum idpr       { value 15; }
            enum ciscoEigrp { value 16; }
            enum dvmrp      { value 17; }
            enum vrrp       { value 18; }
        }
            
        reference
            "The reference RFCs go here.";
    }
    
    typedef time-interval-day { 
        type uint32;
        units "Days";
    }    
    
    typedef time-interval-hour { 
        type uint32;
        units "Hours";
    }    

    typedef time-interval-minute { 
        type uint32;
        units "Minutes";
    }    

    typedef time-interval-sec { 
        type uint32;
        units "Seconds";
    }    
    
    typedef time-interval-msec { 
        type uint32;
        units "milliSeconds";
    }

    typedef time-interval-musec { 
        type uint32;
        units "microSeconds";
    }

    typedef ui32-range {
        type string {
            pattern "[0-9]+(-[0-9]+)?(,[0-9]+(-[0-9]+)?)*";
        }
    }


	typedef slot-id-type
	{
		type string {
			length "1..16"  {
                description
                    "WORD:1-16;;Slot name in [mapped ID]/slot format.";
            }
		}
	}

    typedef chip-id-type {
        type uint8 {
            range 1..9 {
                description
                    "Chip-ID;;  1..9";
            } /* range */
        } /* type  */
    } /* chip-id-type  */

	typedef slot-chip-id-type
	{
		type string {
            length "3..16"  {
            }
        }
    }

    typedef rbridge-id-type {
        type uint32 { 
            range "1..239" {
                error-message
                    "Invalid rbridgeId (must be in the range 1-239).";
            }
        }
    }

    typedef rbridge-id-all-type {
        type union {
            type rbridge-id-type;
            type string {
                pattern "all";
            }
        }
    }

    typedef rbridge-id-all-range-type {
        type union {
            type rbridge-id-type;
            type string;
        }
    }
	 
    typedef feature-type {
        type string {
            length 1..256;
        }
    }

	typedef domain-id-type {
	    type uint32 {
	        range 1..239 {
	        error-message 
                "Invalid domainId (must be in the range 1..239)";
	    }
	}
	}

	typedef mcast-priority-type {
		type uint32 {
			range 1..255 {
				error-message "Invalid Priority Value (must be in the range 1..255)";
			}
		}
	}

	typedef idid-mode-type {
		type enumeration {
			enum disable;
			enum enable;
		}
	}

	typedef mac-address-mcast-type {
        type string {
			pattern '[0-9a-fA-F][13579BDFbdf][0-9a-fA-F][0-9a-fA-F]\.[0-9a-fA-F][0-9a-fA-F][0-9a-fA-F][0-9a-fA-F]\.[0-9a-fA-F][0-9a-fA-F][0-9a-fA-F][0-9a-fA-F]';
        }
    }

	typedef name-string32 {
		type string {
			pattern '[a-zA-Z]{1}([-a-zA-Z0-9\.\\\\@#\+\*\(\)=\{~\}%<>=$_\[\]\|]{0,31})';
		}
	}

	typedef name-string64 {
		type string {
			pattern '[a-zA-Z]{1}([-a-zA-Z0-9\.\\\\@#\+\*\(\)=\{~\}%<>=$_\[\]\|]{0,63})';
		}
	}
	
	typedef name-string63 {
		type string {
			pattern '[a-zA-Z]{1}([-a-zA-Z0-9\.\\\\@#\+\*\(\)=\{~\}%<>=$_\[\]\|]{0,62})';
		}
	}

    typedef name-string128 {
          type string {
              pattern '[a-zA-Z]{1}([-a-zA-Z0-9\.\\\\@#\+\*\(\)=\{~\}%<>=$_\[\]\|]{0,127})';
        }
    }

    typedef wwn-type {
        type string {
        pattern '[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]';
        }
        reference 
            "t11 standard, Fibre Channel Framing and Signaling (FC-FS) 
            Rev 1.70 - Section 14 Name_Indentifier Formats.";
    }
    typedef timezone {
        type enumeration {
            enum Etc/GMT;
            enum Europe/Andorra;
            enum Asia/Dubai;
            enum Asia/Kabul;
            enum America/Antigua;
            enum America/Anguilla;
            enum Europe/Tirane;
            enum Asia/Yerevan;
            enum America/Curacao;
            enum Africa/Luanda;
            enum Antarctica/McMurdo;
            enum Antarctica/South_Pole;
            enum Antarctica/Rothera;
            enum Antarctica/Mawson;
            enum Antarctica/Davis;
            enum Antarctica/Casey;
            enum Antarctica/Vostok;
            enum Antarctica/DumontDUrville;
            enum Antarctica/Syowa;
            enum America/Argentina/Buenos_Aires;
            enum America/Argentina/Cordoba;
            enum America/Argentina/San_Luis;
            enum America/Argentina/Jujuy;
            enum America/Argentina/Tucuman;
            enum America/Argentina/Catamarca;
            enum America/Argentina/La_Rioja;
            enum America/Argentina/San_Juan;
            enum America/Argentina/Mendoza;
            enum America/Argentina/Rio_Gallegos;
            enum America/Argentina/Ushuaia;
            enum Pacific/Pago_Pago;
            enum Europe/Vienna;
            enum Australia/Lord_Howe;
            enum Australia/Hobart;
            enum Australia/Currie;
            enum Australia/Melbourne;
            enum Australia/Sydney;
            enum Australia/Brisbane;
            enum Australia/Lindeman;
            enum Australia/Adelaide;
            enum Australia/Darwin;
            enum Australia/Perth;
            enum Australia/Eucla;
            enum America/Aruba;
            enum Europe/Mariehamn;
            enum Asia/Baku;
            enum Europe/Sarajevo;
            enum America/Barbados;
            enum Asia/Dhaka;
            enum Europe/Brussels;
            enum Africa/Ouagadougou;
            enum Europe/Sofia;
            enum Asia/Bahrain;
            enum Africa/Bujumbura;
            enum Africa/Porto-Novo;
            enum America/St_Barthelemy;
            enum Atlantic/Bermuda;
            enum Asia/Brunei;
            enum America/La_Paz;
            enum America/Noronha;
            enum America/Belem;
            enum America/Fortaleza;
            enum America/Recife;
            enum America/Araguaina;
            enum America/Maceio;
            enum America/Bahia;
            enum America/Sao_Paulo;
            enum America/Campo_Grande;
            enum America/Cuiaba;
            enum America/Santarem;
            enum America/Porto_Velho;
            enum America/Boa_Vista;
            enum America/Manaus;
            enum America/Eirunepe;
            enum America/Rio_Branco;
            enum America/Nassau;
            enum Asia/Thimphu;
            enum Africa/Gaborone;
            enum Europe/Minsk;
            enum America/Belize;
            enum America/St_Johns;
            enum America/Halifax;
            enum America/Glace_Bay;
            enum America/Moncton;
            enum America/Goose_Bay;
            enum America/Blanc-Sablon;
            enum America/Montreal;
            enum America/Toronto;
            enum America/Nipigon;
            enum America/Thunder_Bay;
            enum America/Iqaluit;
            enum America/Pangnirtung;
            enum America/Resolute;
            enum America/Rankin_Inlet;
            enum America/Winnipeg;
            enum America/Rainy_River;
            enum America/Regina;
            enum America/Swift_Current;
            enum America/Edmonton;
            enum America/Cambridge_Bay;
            enum America/Yellowknife;
            enum America/Inuvik;
            enum America/Dawson_Creek;
            enum America/Vancouver;
            enum America/Whitehorse;
            enum America/Dawson;
            enum Indian/Cocos;
            enum Africa/Kinshasa;
            enum Africa/Lubumbashi;
            enum Africa/Bangui;
            enum Africa/Brazzaville;
            enum Europe/Zurich;
            enum Africa/Abidjan;
            enum Pacific/Rarotonga;
            enum America/Santiago;
            enum Pacific/Easter;
            enum Africa/Douala;
            enum Asia/Shanghai;
            enum Asia/Harbin;
            enum Asia/Chongqing;
            enum Asia/Urumqi;
            enum Asia/Kashgar;
            enum America/Bogota;
            enum America/Costa_Rica;
            enum America/Havana;
            enum Atlantic/Cape_Verde;
            enum Indian/Christmas;
            enum Asia/Nicosia;
            enum Europe/Prague;
            enum Europe/Berlin;
            enum Africa/Djibouti;
            enum Europe/Copenhagen;
            enum America/Dominica;
            enum America/Santo_Domingo;
            enum Africa/Algiers;
            enum America/Guayaquil;
            enum Pacific/Galapagos;
            enum Europe/Tallinn;
            enum Africa/Cairo;
            enum Africa/El_Aaiun;
            enum Africa/Asmara;
            enum Europe/Madrid;
            enum Africa/Ceuta;
            enum Atlantic/Canary;
            enum Africa/Addis_Ababa;
            enum Europe/Helsinki;
            enum Pacific/Fiji;
            enum Atlantic/Stanley;
            enum Pacific/Truk;
            enum Pacific/Ponape;
            enum Pacific/Kosrae;
            enum Atlantic/Faroe;
            enum Europe/Paris;
            enum Africa/Libreville;
            enum Europe/London;
            enum America/Grenada;
            enum Asia/Tbilisi;
            enum America/Cayenne;
            enum Europe/Guernsey;
            enum Africa/Accra;
            enum Europe/Gibraltar;
            enum America/Godthab;
            enum America/Danmarkshavn;
            enum America/Scoresbysund;
            enum America/Thule;
            enum Africa/Banjul;
            enum Africa/Conakry;
            enum America/Guadeloupe;
            enum Africa/Malabo;
            enum Europe/Athens;
            enum Atlantic/South_Georgia;
            enum America/Guatemala;
            enum Pacific/Guam;
            enum Africa/Bissau;
            enum America/Guyana;
            enum Asia/Hong_Kong;
            enum America/Tegucigalpa;
            enum Europe/Zagreb;
            enum America/Port-au-Prince;
            enum Europe/Budapest;
            enum Asia/Jakarta;
            enum Asia/Pontianak;
            enum Asia/Makassar;
            enum Asia/Jayapura;
            enum Europe/Dublin;
            enum Asia/Jerusalem;
            enum Europe/Isle_of_Man;
            enum Asia/Kolkata;
            enum Indian/Chagos;
            enum Asia/Baghdad;
            enum Asia/Tehran;
            enum Atlantic/Reykjavik;
            enum Europe/Rome;
            enum Europe/Jersey;
            enum America/Jamaica;
            enum Asia/Amman;
            enum Asia/Tokyo;
            enum Africa/Nairobi;
            enum Asia/Bishkek;
            enum Asia/Phnom_Penh;
            enum Pacific/Tarawa;
            enum Pacific/Enderbury;
            enum Pacific/Kiritimati;
            enum Indian/Comoro;
            enum America/St_Kitts;
            enum Asia/Pyongyang;
            enum Asia/Seoul;
            enum Asia/Kuwait;
            enum America/Cayman;
            enum Asia/Almaty;
            enum Asia/Qyzylorda;
            enum Asia/Aqtobe;
            enum Asia/Aqtau;
            enum Asia/Oral;
            enum Asia/Vientiane;
            enum Asia/Beirut;
            enum America/St_Lucia;
            enum Europe/Vaduz;
            enum Asia/Colombo;
            enum Africa/Monrovia;
            enum Africa/Maseru;
            enum Europe/Vilnius;
            enum Europe/Luxembourg;
            enum Europe/Riga;
            enum Africa/Tripoli;
            enum Africa/Casablanca;
            enum Europe/Monaco;
            enum Europe/Chisinau;
            enum Europe/Podgorica;
            enum America/Marigot;
            enum Indian/Antananarivo;
            enum Pacific/Majuro;
            enum Pacific/Kwajalein;
            enum Europe/Skopje;
            enum Africa/Bamako;
            enum Asia/Rangoon;
            enum Asia/Ulaanbaatar;
            enum Asia/Hovd;
            enum Asia/Choibalsan;
            enum Asia/Macau;
            enum Pacific/Saipan;
            enum America/Martinique;
            enum Africa/Nouakchott;
            enum America/Montserrat;
            enum Europe/Malta;
            enum Indian/Mauritius;
            enum Indian/Maldives;
            enum Africa/Blantyre;
            enum America/Mexico_City;
            enum America/Cancun;
            enum America/Merida;
            enum America/Monterrey;
            enum America/Mazatlan;
            enum America/Chihuahua;
            enum America/Hermosillo;
            enum America/Tijuana;
            enum Asia/Kuala_Lumpur;
            enum Asia/Kuching;
            enum Africa/Maputo;
            enum Africa/Windhoek;
            enum Pacific/Noumea;
            enum Africa/Niamey;
            enum Pacific/Norfolk;
            enum Africa/Lagos;
            enum America/Managua;
            enum Europe/Amsterdam;
            enum Europe/Oslo;
            enum Asia/Katmandu;
            enum Pacific/Nauru;
            enum Pacific/Niue;
            enum Pacific/Auckland;
            enum Pacific/Chatham;
            enum Asia/Muscat;
            enum America/Panama;
            enum America/Lima;
            enum Pacific/Tahiti;
            enum Pacific/Marquesas;
            enum Pacific/Gambier;
            enum Pacific/Port_Moresby;
            enum Asia/Manila;
            enum Asia/Karachi;
            enum Europe/Warsaw;
            enum America/Miquelon;
            enum Pacific/Pitcairn;
            enum America/Puerto_Rico;
            enum Asia/Gaza;
            enum Europe/Lisbon;
            enum Atlantic/Madeira;
            enum Atlantic/Azores;
            enum Pacific/Palau;
            enum America/Asuncion;
            enum Asia/Qatar;
            enum Indian/Reunion;
            enum Europe/Bucharest;
            enum Europe/Belgrade;
            enum Europe/Kaliningrad;
            enum Europe/Moscow;
            enum Europe/Volgograd;
            enum Europe/Samara;
            enum Asia/Yekaterinburg;
            enum Asia/Omsk;
            enum Asia/Novosibirsk;
            enum Asia/Krasnoyarsk;
            enum Asia/Irkutsk;
            enum Asia/Yakutsk;
            enum Asia/Vladivostok;
            enum Asia/Sakhalin;
            enum Asia/Magadan;
            enum Asia/Kamchatka;
            enum Asia/Anadyr;
            enum Africa/Kigali;
            enum Asia/Riyadh;
            enum Pacific/Guadalcanal;
            enum Indian/Mahe;
            enum Africa/Khartoum;
            enum Europe/Stockholm;
            enum Asia/Singapore;
            enum Atlantic/St_Helena;
            enum Europe/Ljubljana;
            enum Arctic/Longyearbyen;
            enum Europe/Bratislava;
            enum Africa/Freetown;
            enum Europe/San_Marino;
            enum Africa/Dakar;
            enum Africa/Mogadishu;
            enum America/Paramaribo;
            enum Africa/Sao_Tome;
            enum America/El_Salvador;
            enum Asia/Damascus;
            enum Africa/Mbabane;
            enum America/Grand_Turk;
            enum Africa/Ndjamena;
            enum Indian/Kerguelen;
            enum Africa/Lome;
            enum Asia/Bangkok;
            enum Asia/Dushanbe;
            enum Pacific/Fakaofo;
            enum Asia/Dili;
            enum Asia/Ashgabat;
            enum Africa/Tunis;
            enum Pacific/Tongatapu;
            enum Europe/Istanbul;
            enum America/Port_of_Spain;
            enum Pacific/Funafuti;
            enum Asia/Taipei;
            enum Africa/Dar_es_Salaam;
            enum Europe/Kiev;
            enum Europe/Uzhgorod;
            enum Europe/Zaporozhye;
            enum Europe/Simferopol;
            enum Africa/Kampala;
            enum Pacific/Johnston;
            enum Pacific/Midway;
            enum Pacific/Wake;
            enum America/New_York;
            enum America/Detroit;
            enum America/Kentucky/Monticello;
            enum America/Indiana/Indianapolis;
            enum America/Indiana/Vincennes;
            enum America/Indiana/Knox;
            enum America/Indiana/Winamac;
            enum America/Indiana/Marengo;
            enum America/Indiana/Vevay;
            enum America/Chicago;
            enum America/Indiana/Tell_City;
            enum America/Indiana/Petersburg;
            enum America/Menominee;
            enum America/North_Dakota/Center;
            enum America/North_Dakota/New_Salem;
            enum America/Denver;
            enum America/Boise;
            enum America/Shiprock;
            enum America/Phoenix;
            enum America/Los_Angeles;
            enum America/Anchorage;
            enum America/Juneau;
            enum America/Yakutat;
            enum America/Nome;
            enum America/Adak;
            enum Pacific/Honolulu;
            enum America/Montevideo;
            enum Asia/Samarkand;
            enum Asia/Tashkent;
            enum Europe/Vatican;     
            enum America/St_Vincent;
            enum America/Caracas;
            enum America/Tortola;
            enum America/St_Thomas;
            enum Asia/Ho_Chi_Minh;
            enum Pacific/Efate;
            enum Pacific/Wallis;
            enum Pacific/Apia;
            enum Asia/Aden;
            enum Indian/Mayotte;
            enum Africa/Johannesburg;
            enum Africa/Lusaka;
            enum Africa/Harare;
            enum Europe/Greenwich;
       }
    }
    
    container show {
		container defaults {
		}
    }

    container clear {
    }

    container no {
    }

    container ip {
    }

    container ipv6 {
    }
		
    container router {
		//tailf:display-when '/vcsmode/vcs-mode = "false"';
        description
            "The routing system.";
    } /* router container */
	
    typedef ipv4-address-prefix-type {
        type string {
            pattern '((0'
                +   '|(1[0-9]{0,2})'
                +   '|(2(([0-4][0-9]?)|(5[0-5]?)|([6-9]?)))'
                +   '|([3-9][0-9]?)'
                +  ')'
                + '\.){3}'
                + '(0'
                +  '|(1[0-9]{0,2})'
                +  '|(2(([0-4][0-9]?)|(5[0-5]?)|([6-9]?)))'
                +  '|([3-9][0-9]?)'
                + ')/(([0-9])|([1-2][0-9])|(3[0-2]))' {
                description
                    "IPv4ADDRESS;;The IPv4 Address/Prefix";
            }
        }
        description
            "The definition to specify the IPv4 address in the
            A.B.C.D/prefix-len format.";
    }


    typedef ipv6-address-prefix {
        type string {
          pattern '((:|[0-9a-fA-F]{0,4}):)([0-9a-fA-F]{0,4}:){0,5}'
                + '((([0-9a-fA-F]{0,4}:)?(:|[0-9a-fA-F]{0,4}))|'
                + '(((25[0-5]|2[0-4][0-9]|[01]?[0-9]?[0-9])\.){3}'
                + '(25[0-5]|2[0-4][0-9]|[01]?[0-9]?[0-9])))'
                + '(/(([0-9])|([0-9]{2})|(1[0-1][0-9])|(12[0-8])))';
          pattern '(([^:]+:){6}(([^:]+:[^:]+)|(.*\..*)))|'
                + '((([^:]+:)*[^:]+)?::(([^:]+:)*[^:]+)?)'
                + '(%.+)?' {
          }
        }
        description
            "The definition to specify the IPv6 address in the
             xxxx:xxxx:xxxx:xxxx:xxxx:xxxx:xxxx:xxxx/prefix-len format.
             The prefix length is given by the number following the
             slash character and must be less than or equal 128.
             A prefix length value of n corresponds to an IP address
             mask that has n contiguous 1-bits from the most
             significant bit (MSB) and all other bits set to 0.

             The IPv6 address should have all bits that do not belong
             to the prefix set to zero.

             The canonical format of an IPv6 prefix has all bits of
             the IPv6 address set to zero that are not part of the
             IPv6 prefix.  Furthermore, IPv6 address is represented
             in the compressed format described in RFC 4291, Section
             2.2, item 2 with the following additional rules: the ::
             substitution must be applied to the longest sequence of
             all-zero 16-bit chunks in an IPv6 address.  If there is
             a tie, the first sequence of all-zero 16-bit chunks is
             replaced by ::.  Single all-zero 16-bit chunks are not
             compressed.  The canonical format uses lowercase
             characters and leading zeros are not allowed.";
             reference
                 "RFC 4291: IP Version 6 Addressing Architecture";

   }

    typedef ve-range-cli-pattern {
        type string {
            pattern '((([1-9][0-9]{0,2})|([1-7][0-9]{3})|(80[0-9]{2})|(81[0-8][0-9])|(819[0-1]))'
                    + '(-(([1-9][0-9]{0,2})|([1-7][0-9]{3})|(80[0-9]{2})|(81[0-8][0-9])|(819[0-1]))){1})|'
                    + '((([1-9][0-9]{0,2})|([1-7][0-9]{3})|(80[0-9]{2})|(81[0-8][0-9])|(819[0-1]))'
                    + '(-(([1-9][0-9]{0,2})|([1-7][0-9]{3})|(80[0-9]{2})|(81[0-8][0-9])|(819[0-1])))?)'
                    + '((,(([1-9][0-9]{0,2})|([1-7][0-9]{3})|(80[0-9]{2})|(81[0-8][0-9])|(819[0-1]))'
                    + '(-(([1-9][0-9]{0,2})|([1-7][0-9]{3})|(80[0-9]{2})|(81[0-8][0-9])|(819[0-1])))?){1})+';
            length "1..253" {
            }
        }
    }

    typedef loopback-range-cli-pattern {
        type string {
            pattern '((([1-9][0-9]{0,1})|(1[0-9]{2})|(2[0-4][0-9])|(25[0-5]))'
                    +  '(-(([1-9][0-9]{0,1})|(1[0-9]{2})|(2[0-4][0-9])|(25[0-5]))){1})|'
                    +  '((([1-9][0-9]{0,1})|(1[0-9]{2})|(2[0-4][0-9])|(25[0-5]))'
                    +  '(-(([1-9][0-9]{0,1})|(1[0-9]{2})|(2[0-4][0-9])|(25[0-5])))?)'
                    +  '((,(([1-9][0-9]{0,1})|(1[0-9]{2})|(2[0-4][0-9])|(25[0-5]))'
                    +  '(-(([1-9][0-9]{0,1})|(1[0-9]{2})|(2[0-4][0-9])|(25[0-5])))?){1})+';
            length "1..253" {
            }
        }
    }

    typedef ipv6-address-host-name {
            type union{
                type inet:ipv6-address;
                type string {
                    pattern '[a-zA-Z]{1}([-a-zA-Z0-9\.\\\\@#\+\*\(\)=\{~\}%<>=$_\[\]\|]{0,127})';
                } 				
            }
    }

}
