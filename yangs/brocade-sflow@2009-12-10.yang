/*********************************************************************
 * brocade-sflow.yang: Brocade SFLOW  module data model                      *
 *                                                                   *
 * March 2011, Venkat                                                *
 *                                                                   *
 * Copyright (c) 2011 by Brocade Communications Systems, Inc.        *
 * All rights reserved.                                              *
 *                                                                   *
 *********************************************************************/

module brocade-sflow {
    namespace "urn:brocade.com:mgmt:brocade-sflow";
    prefix "sflow";

    /* Linkage Statements */

    import ietf-inet-types {
        prefix inet;
    }
    import tailf-common{
        prefix tailf;
    }


    import brocade-interface {
        prefix interface;

    }

    /* Meta Information */
    
    organization
        "Brocade Communications";

    contact
        "Brocade Communications Systems, Inc.
         Postal: 130 Holger Way
                 San Jose, CA 95134
                 U.S.A
         Tel: +1-408-333-8000
         E-mail: support@Brocade.com
         web: www.brocade.com.";

    description
        "This submodule describes the data model for sFlow";

    /* Revision history */

    revision "2009-12-10" {
        description "Initial Version";
    }

    /* Module Definition */

    grouping sflow-config {
        leaf polling-interval {
            default 20;
            type uint32 {
                range "1..65535" {
                }
            }
        }
        leaf sample-rate {
            default 32768;
            type uint32 {
                range "2..16777215" {
                }
            }
        }
    }

    grouping common-phy-sflow-cmds {
        container sflow {
            leaf enable {
                type empty;
            }
            uses sflow-config;
        }
    }

	typedef profile-name-type {
		type string {
			pattern '[a-zA-Z]{1}([-a-zA-Z0-9_]{0,63})' {
			}
        }	
	}

    container sflow {
        
        leaf enable {
            type empty;
        }


        list collector {
            key "collector-ip-address collector-port-number";
            unique "collector-ip-address collector-port-number";
            leaf collector-ip-address  {
                type inet:ip-address;
            }
            leaf collector-port-number  {
                type uint32 {
                    range "1..65535" {
                    }
                }
            }
        }
            
		leaf source-ip { 
			type enumeration {
				enum chassis-ip {
					value 1;
				}
				enum mm-ip  {
					value 2;
				}
			}
		}  


        uses sflow-config;
    }
    
    list sflow-profile {
        key profile-name;      
        //unique "profile-name";      
        leaf profile-name {
            mandatory true;
            type profile-name-type;
        }
        leaf profile-sampling-rate {
            type uint32 {
                range "2..8388608" {
                }
            }
        }
    }    

    augment "/interface:interface/interface:tengigabitethernet" {
        uses common-phy-sflow-cmds;
    }
    augment "/interface:interface/interface:gigabitethernet" {
        uses common-phy-sflow-cmds;
    }
    augment "/interface:interface/interface:fortygigabitethernet" {
        uses common-phy-sflow-cmds;
    }
    augment "/interface:interface/interface:hundredgigabitethernet" {
        uses common-phy-sflow-cmds;
    }
}
