module tailf-webui {

  namespace "http://tail-f.com/ns/webui";

  prefix "webui";

  import ietf-netconf-acm {
    prefix nacm;
  }

  import tailf-common {
    prefix tailf;
  }

  organization "Tail-f Systems";

  description
    "This module defines the Tail-f Web UI data model";

  revision 2013-03-07 {
    description
      "Initial release containing graphical panel and data storage support";
  }

  container webui {
    tailf:info "Web UI specific configuration";

    container schematics {
      tailf:info "Diagrams and reusable assets for the same";
      container panels {
        tailf:info "For drawing diagrams";
        list panel {
          tailf:info "Diagrams containing images and other components";
          key "name";
          leaf name {
            tailf:info "A unique name for the panel";
            type string;
          }
          container properties {
            tailf:info "Optional panel properties";
            leaf title {
              tailf:info "The panel heading";
              type string;
            }
            leaf description {
              tailf:info "What this panel is about";
              type string;
            }
            leaf width {
              tailf:info "Width in pixels";
              type uint16;
            }
            leaf height {
              tailf:info "Height in pixels";
              type uint16;
            }
          }
          container components {
            tailf:info "";

            list component {
              key "id";

              leaf id {
                tailf:info "Identifies this component uniquely.";
                type string;
              }

              container properties {
                leaf top {
                  tailf:info "Top-to-bottom coordinate in pixels";
                  type uint16;
                }
                leaf left {
                  tailf:info "Left-to-right coordinate in pixels";
                  type uint16;
                }
                leaf width {
                  tailf:info "Width in pixels";
                  type uint16;
                }
                leaf height {
                  tailf:info "Height in pixels";
                  type uint16;
                }
                leaf z-index {
                  tailf:info "How the components are stacked on the z-axis";
                  type int16;
                }
                choice component-type {
                  mandatory true;
                  case image {
                    container image {
                      leaf image {
                        mandatory true;
                        tailf:info "The image to display";
                        type leafref {
                          path "/webui/schematics/assets/asset/name";
                        }
                      }
                    }
                  }
                  case link {
                    container link {
                      leaf text {
                        tailf:info "The link text";
                        type string;
                      }
                      leaf link {
                        mandatory true;
                        tailf:info "The link itself";
                        type string;
                      }
                    }
                  }
                }
              }
            }
          }
        }
      }
      container assets {
        tailf:info "Sharable assets such as images and movies";
        list asset {
          key "name";
          leaf name {
            tailf:info "A unique name for the asset";
            type string;
          }
          choice asset-type {
            case image {
              leaf base-64-image {
                mandatory true;
                tailf:info "Base64 encoded image";
                type string;
              }
              leaf type {
                mandatory true;
                tailf:info "Image file format";
                type enumeration {
                  enum jpeg;
                  enum png;
                  enum gif;
                }
              }
            }
          }
        }
      }
    }
    container data-stores {
      tailf:info "Persistent data-stores used by the Web UI";

      list user-profile {
        nacm:default-deny-all;
        tailf:info "Stores profiles for specific users in JSON format";
        key "username";

        leaf username {
          type string;
          tailf:info "Who the configuration belongs to";
        }

        list profile {
          tailf:info "User profile settings";
          key "key";
          uses base-key-value-store;
        }
        list saved-query {
          tailf:info "Saved search queries";
          key "key";
          uses base-key-value-store;
        }
      }

      list data-store {
        tailf:info "Stores ad-hoc configuration";
        key "key";
        uses base-key-value-store;
      }

      list saved-query {
        tailf:info "Queries that have been saved globally";
        key "key";
        uses base-key-value-store;
      }
    }
  }

  grouping base-key-value-store {
    leaf key {
      type string;
      tailf:info "Identifies a unique entry in the store";
    }
    leaf value {
      type string;
      tailf:info "String based blob, for example JSON or base64 encoded string";
    }
  }
}
