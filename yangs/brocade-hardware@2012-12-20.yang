/******************************************************************
* brocade-hardware.yang: Brocade Hardware Management Data Model 
*
* December 2012, Venkat Pogiri
*
* Copyright (c) 2014 by Brocade Communications Systems, Inc.
* All rights reserved.
*******************************************************************/
module brocade-hardware {
    namespace "urn:brocade.com:mgmt:brocade-hardware";
    prefix "hardware";

    /* Linkage Statements */

    import tailf-common {
        prefix tailf;
    }

    import brocade-interface {
        prefix interface; 
    }

    import brocade-common-def {
        prefix common-def;
    }

    import brocade-rbridge {
        prefix rbridge;
    }

    /* Meta Information */

    organization
        "Brocade Communications Systems, Inc.";

    contact
        "Brocade Communications Systems, Inc.
         Postal: 130 Holger Way
                 San Jose, CA 95134
                  U.S.A
         Tel: +1-408-333-8000
         E-mail: support@Brocade.com
         web: www.brocade.com.";

    description
        "This hardware management module is used to manage connectors.
         It can be used to breakout the connectors and set the type
         of the connectors.";

    /* Revision history */

    revision "2012-12-20" {
        description
            "Initial version of this management module.";
    }

    /* Module Definition */

    typedef u-port-type {
        type enumeration {
            enum ethernet {
                value 1;
            }
            enum fibre-channel {
                value 2;
            }
        }
    }

	typedef connector-speed-type {
		type enumeration {
			enum LowMixed {
				value 0;
			}
			enum HighMixed {
				value 1;
			}
			enum FibreChannel {
				value 2;
			}
		}
	}

	typedef connector-group-type {
		type string {
			pattern '((([1-9]|[1-9][0-9]|1[0-9][0-9]|2[0-3][0-9])/)?(([0-9]|[1][0-6]))/([1-9]|[1-9][0-9])(:[1-4])?)';
			length "3..16"  {
			}
		}
	}

	typedef interface-type {
		type string {
			pattern '((([1-9]|[1-9][0-9]|1[0-9][0-9]|2[0-3][0-9])/)?(([0-9]|[1][0-6]))/([1-9]|[1-9][0-9])(:[1-4])?)';
			length "3..16"  {
			}
		}

		description
			"The definition for specifying a network interface name in
			a VCS environment. It is in 3-tuple canonical format:
			[rbridge-id]/slot/port.";
	}

	typedef port-type {
		type enumeration {
			enum fibre-channel {
				value 0;
				description "A FirbeChannel Port";
			}
			enum ethernet {
				value 1;
				description "An Ethernet Port";
			}
		}

		description "Definition for specifying the type of port.";
    }

    container hardware {
        description 
            "This specifies the group of configuration/operational 
            elements to manage the hardware chracteristics of this
            managed entity."; 
        list connector {
            key "name";

            leaf name {
                type interface:interface-type;
                mandatory true;
            }
            container sfp {
                leaf breakout {
                    type empty;
                }
            }
        }


        list port-group {
            key "name";

            leaf name {
                type interface:port-group-type;
                mandatory true;
            }

            container mode {
                /*tailf:cli-incomplete-command;
                *tailf:cli-incomplete-no; */
                leaf performance {
                    type empty;
                }
            }
        }

		list connector-group {
			key "id";

			leaf id {
				type connector-group-type;
			}

			leaf speed {
				type connector-speed-type;
            }
        }

		list flexport {
			key id;

			leaf id {
				type interface-type;
				mandatory true;
				description "The port to be changed.";
			}

			container flexport_type {
				leaf type {
					type port-type;
					description "The type to be configured.";
				}

				leaf instance {
					type int32;
					description "The instance to which the port should be configured.";
				}

				leaf skip_deconfig {
					type empty;
					description "Skip plugin notification Errors.";
				}
			}
		}
	}

	typedef tcam-profile-subtype {
		type enumeration {
			enum default {
				value 0;
			}

			enum l2-ipv4-acl {
				value 1;
			}

			enum l2-acl-qos {
				value 2;
			}

			enum ipv4-v6-pbr {
				value 3;
			}

			enum ipv4-v6-qos {
				value 4;
			}

			enum ipv4-v6-mcast {
				value 5;
			}
		}
	}

	typedef routing-profile-subtype {
		type enumeration {
			enum default {
				value 0;
			}

			enum ipv4-max-route {
				value 1;
            }
 
            enum ipv4-max-arp {
				value 2;
			}

			enum ipv4-min-v6 {
				value 3;
			}
 
			enum ipv6-max-route {
				value 4;
			}
 
			enum ipv6-max-nd {
				value 5;
			}
		}
	}

	grouping profile-cmds {
		container hardware-profile {

			container tcam {

				container predefined {
 
					leaf tcam_profiletype {
						type tcam-profile-subtype;
					}
				}
			}

			container route-table {

				container predefined {

					leaf routing_profiletype {
						type routing-profile-subtype;
					}
				}
			}
		}
	}

	augment "/rbridge:rbridge-id" {
		uses profile-cmds;
	}

	augment "/common-def:show" {
		container hardware {
			tailf:action connector-group {
				input {}
				output {}
			}
		}

		container hardware-profile {

			tailf:action hardware-profile {

			input {
				choice profile-type {
				case tcam {
					leaf tcam {
					    type tcam-profile-subtype;
						mandatory true;
					}
				}	

				case route-table {
					leaf route-table {
						type routing-profile-subtype;
						mandatory true;
					}
				}

				case current {
					leaf current {
						type empty;
						mandatory true;
					} 
				}
				}

				leaf rbridge-id {
					type common-def:rbridge-id-all-type;
					mandatory false;
				}
			}
			output {}
			}
		}
	}

	rpc get-flexports {
		output {
			list flexport-list {
				leaf port-id {
					type string;
                }
            }
       }
    }
}
