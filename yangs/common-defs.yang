// YANG submodule for common definitions.
// Revisions:
//     2011-04-20: Initial version.
//

module common-defs 
{
    namespace "http://brocade.com/ns/netconf/config/netiron-config/";
    prefix "common";

    organization 
        "Brocade Communications Inc.";

    contact
             "Technical Support Center"+
             "130 Holger Way,"+
             "San Jose, CA  95134"+
             "Email:  ipsupport@brocade.com"+
             "Phone: 1-800-752-8061"+
             "URL:  www.brocade.com";

    description "This module defines the common definitions. VERSION: V5.8.00a";
    
    revision 2011-04-20
    {
        description "Initial revision";
    }


    typedef interface-all-types
    {
        type string
        {
            pattern 
                 "ethernet\s+\d{1,2}/\d{1,2}|"+
                 "ethernet\s+\d{1,2}/\d{1,2}\s+to\d{1,2}/\d{1,2}|"+
                 "pos\s+\d{1,2}/\d{1,2}|"+
                 "pos\s+\d{1,2}/\d{1,2}\s+to\d{1,2}/\d{1,2}|"+
                 "ve\s+\d|"+
                 "loopback\s+\d|"+
                 "management\s+\d|"+
                 "tunnel\s+\d";
            
                  length "11..100";
        }
        description 
            "Single or range of interfaces "+
            "Format is etherenet SLOT/PORT or "+
            "etherent SLOT/PORT to SLOT/PORT "+
            "pos SLOT/PORT "+
            "pos SLOT/PORT to SLOT/PORT "+
            "ve ve_id "+
            "loopback loopback_id (1 to 64) "+
            "management mgmt_id (1 or 2) "+
            "tunnel runnel_id";
    }

    typedef interface-eth-pos-ve-multiple
    {
        type string
        {
            pattern 
                 "ethernet\s+\d{1,2}/\d{1,2}|"+
                 "ethernet\s+\d{1,2}/\d{1,2}\s+to\d{1,2}/\d{1,2}|"+
                 "pos\s+\d{1,2}/\d{1,2}|"+
                 "pos\s+\d{1,2}/\d{1,2}\s+to\d{1,2}/\d{1,2}|"+
                 "ve\s+\d";
            
                  length "11..100";
        }
        description 
            "Single or range of interfaces "+
            "Format is etherenet SLOT/PORT or "+
            "etherent SLOT/PORT to SLOT/PORT "+
            "pos SLOT/PORT "+
            "pos SLOT/PORT to SLOT/PORT "+
            "ve ve_id";
    }

    typedef interface-eth-pos-ve-single
    {
        type string
        {
            pattern 
                 "ethernet\s+\d{1,2}/\d{1,2}|"+
                 "pos\s+\d{1,2}/\d{1,2}|"+
                 "ve\s+\d";
            
                  length "11..100";
        }
        description 
            "Single or range of interfaces "+
            "Format is etherenet SLOT/PORT or "+
            "pos SLOT/PORT "+
            "ve ve_id";
    }

    typedef ethernet-intf-single
    {
        type string
        {
            pattern "ethernet\s+\d{1,2}/\d{1,2}";
            length "11..20";
        }
        description "Single ethernet interface";
    }

    typedef ethernet-pos-intf-single
    {
        type string
        {
            pattern 
                "ethernet\s+\d{1,2}/\d{1,2}|"+
                "pos\s+\d{1,2}/\d{1,2}";
            length "11..20";
        }
        description "Single ethernet or pos interface";
    }

    typedef ve-intf-single
    {
        type string
        {
            pattern "ve\s+\d";
            length "4..20";
        }
        description "VE interface";
    }

    typedef ethernet-intf-multiple
    {
        type string
        {
            pattern 
                 "ethernet\s+\d{1,2}/\d{1,2}|"+
                 "ethernet\s+\d{1,2}/\d{1,2}\s+to\d{1,2}/\d{1,2}";
            length "11..50";
        }
        description "Multiple ethernet interfaces";
    }

    typedef ethernet-pos-intf-multiple
    {
        type string
        {
            pattern 
                 "ethernet\s+\d{1,2}/\d{1,2}|"+
                 "ethernet\s+\d{1,2}/\d{1,2}\s+to\d{1,2}/\d{1,2}|"+
                 "pos\s+\d{1,2}/\d{1,2}|"+
                 "pos\s+\d{1,2}/\d{1,2}\s+to\d{1,2}/\d{1,2}";
            length "11..50";
        }
        description "Multiple ethernet or pos interfaces";
    }
    
    typedef vlan-identifier
    {
        type uint32
        {
            range "1..4090";
        }
        description "VLAN Identifier";
    }
    
    typedef ipv4_address
    {
//      type "inet:ipv4-address";
        type string
        {
            length "7..15";
        }
        description "IPv4 Address";
    }

    typedef ipv6_address
    {
//      type "inet:ipv6-address";
        type string
        {
            length "3..39";
        }
        description "IPv6 Address";
    }

    typedef ipv4_address_mask
    {
        type string
        {
            length "9..19";
        }
        description "IPv4 Address/mask";
    }

    typedef ipv6_address_mask
    {
        type string
        {
            length "6..43";
        }
        description "IPv6 Address/mask";
    }
    
    
    typedef mac_address
    {
//      type yang:mac-address;
        type string 
        {
            length "1..21";
        }
        description "Ethernet MAC address";
    }
    typedef priority-value
    {
        type uint32
        {
            range "0..7";
        }
        description "Priority Value";
    }
    
    grouping priority-grouping
    {
        description "Priority";   
        container priority
        {
            description "Priority";
            leaf value 
            {
                type priority-value; 
                description "Priority value";
            }
            leaf force 
            {
                type empty;
                description "Priority force";
            }
        }//end container priority-value
        
    }//end grouping priority-grouping
    
}//end module common-defs
