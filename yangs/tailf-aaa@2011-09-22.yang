module tailf-aaa {
  namespace "http://tail-f.com/ns/aaa/1.1";
  prefix aaa;
  tailf:id "http://tail-f.com/ns/aaa";

  import tailf-common {
    prefix tailf;
  }

  organization "Tail-f Systems";

  description
    "This module defines the Tail-f AAA data model.";

  revision 2011-09-22 {
    description
      "Released as part of ConfD-3.7.";
  }

  revision 2010-06-17 {
    description
      "Released as part of ConfD-3.3.";
  }

  revision 2010-04-22 {
    description
      "Released as part of ConfD-3.2.1.";
  }

  revision 2010-03-18 {
    description
      "Released as part of ConfD-3.2.";
  }

  typedef history {
    type uint64 {
      range "0 .. 8192";
    }
  }
  typedef idle-timeout {
    type uint64 {
      range "0 .. 8192";
    }
  }
  typedef display-level {
    type uint64 {
      range "1 .. 64";
    }
  }
  typedef dataOperationType {
    type enumeration {
      enum r;
      enum x;
      enum rx;
      enum w;
      enum rw;
      enum wx;
      enum rwx;
      enum c;
      enum cr;
      enum cu;
      enum cd;
      enum cx;
      enum cru;
      enum crd;
      enum crx;
      enum cud;
      enum cux;
      enum cdx;
      enum crud;
      enum crux;
      enum crdx;
      enum cudx;
      enum crudx;
      enum ru;
      enum rd;
      enum rud;
      enum rux;
      enum rdx;
      enum u;
      enum ud;
      enum ux;
      enum d;
      enum dx;
    }
  }
  typedef cmdOperationType {
    type enumeration {
      enum r;
      enum x;
      enum rx;
    }
  }
  typedef Action {
    type enumeration {
      enum accept;
      enum reject;
      enum accept_log;
    }
  }
  typedef passwdStr {
    type tailf:md5-digest-string {
    }
  }
  typedef levelInt {
    type int32 {
      range "0 .. 15";
    }
  }
  typedef modeStr {
    type union {
      type string;
      type builtinModes;
    }
  }
  typedef builtinModes {
    type enumeration {
      enum exec;
      enum configure;
    }
  }
  
  grouping session-params {
    leaf complete-on-space {
      type boolean;
      tailf:info "Enable/disable completion on space";
    }
    leaf ignore-leading-space {
      type boolean;
      tailf:info "Ignore leading whitespace";
    }
    leaf idle-timeout {
      config false;
      type idle-timeout;
      tailf:callpoint idletimeout_cp;
      tailf:info "CLI idle-timeout in seconds";
    }
    leaf paginate {
      type boolean;
      tailf:info "Paginate output from CLI commands";
    }
    leaf history {
      type history;
      tailf:info "History size";
    }
    leaf autowizard {
      type boolean;
      tailf:info "Automatically query user for mandatory elems";
    }
    leaf show-defaults {
      type boolean;
      tailf:info "Show default values when showing the configuration";
    }
    leaf display-level {
      type display-level;
      tailf:info "Max depth to show when displaying configuration";
    }
    leaf prompt1 {
      type string;
      tailf:info "Prompt for operational mode";
    }
    leaf prompt2 {
      type string;
      tailf:info "Prompt for configure mode";
    }
  }

  container aaa {
    tailf:hidden full;
    container authentication {
      container users {
        list user {
          tailf:callpoint user_cp;
          key name;
          max-elements 1024;
          leaf name {
            type string;
          }
          leaf uid {
            type int32;
            mandatory true;
          }
          leaf gid {
            type int32;
            mandatory true;
          }
          leaf password {
            type passwdStr;
            mandatory true;
          }
          leaf ssh_keydir {
            type string;
            mandatory true;
          }
          leaf homedir {
            type string;
            mandatory true;
          }
        }
      }
      container groups {
        list group {
          tailf:callpoint role_cp;
          key name;
          max-elements 32;
          leaf name {
            type string;
          }
          leaf gid {
            type int32;
          }
          leaf users {
            type string;
            mandatory true;
          }
        }
      }
    }
    container authorization {
      container cmdrules {
        list cmdrule {
          tailf:callpoint cmdrule_cp;
          key index;
          tailf:indexed-view;

          leaf index {
            type uint32;
          }
          leaf context {
            type string;
            mandatory true;
          }
          leaf command {
            type string;
            mandatory true;
          }
          leaf group {
            type string;
            mandatory true;
          }
          leaf ops {
            type cmdOperationType;
            mandatory true;
          }
          leaf action {
            type Action;
            mandatory true;
          }
        }
      }
      container datarules {
        list datarule {
          tailf:callpoint datarule_cp;
          key index;
          tailf:indexed-view;

          leaf index {
            type uint32;
          }
          leaf namespace {
            type string;
            mandatory true;
          }
          leaf context {
            type string;
            default *;
          }
          leaf keypath {
            type string;
            mandatory true;
          }
          leaf group {
            type string;
            mandatory true;
          }
          leaf ops {
            type dataOperationType;
            mandatory true;
          }
          leaf action {
            type Action;
            mandatory true;
          }
        }
      }
    }
    container ios {
      presence "";

      list level {
        key nr;
        min-elements 2;
        leaf nr {
          type levelInt;
        }
        leaf secret {
          type passwdStr;
        }
        leaf password {
          type passwdStr;
        }
        leaf prompt {
          type string;
          default "\h# ";
        }
      }

      list privilege {
        key mode;
        leaf mode {
          type modeStr;
        }
        list level {
          key nr;
          min-elements 1;
          max-elements 15;
          leaf nr {
            type levelInt;
          }
          list command {
            key name;
            leaf name {
              type string;
            }
          }
        }
      }
    }
  }
  list alias {
    tailf:hidden full;
    tailf:callpoint ConfdCliCommandGlobalAliasCallpoint;
    key name;
    tailf:info "Create command alias.";
    leaf name {
      type string;
      tailf:info "Name of the command alias. An alias name can be a single 
                  word or multiple words joined by a dash (-).";
    }
    leaf expansion {
      type string;
      mandatory true;
      tailf:info "Original command syntax. Valid abbreviations of the original 
                  command syntax can be entered for the command-syntax argument.";
    }
  }
  container session {
    tailf:hidden full;
    uses session-params;
    presence "";
    tailf:info "Global default CLI session parameters";
  }
  list user {
    tailf:hidden full;
    tailf:callpoint ConfdAliasUserCallpoint;
    key name;
    leaf name {
      type string;
    }
    leaf description {
      type string;
      tailf:info "User description";
    }
    list alias {
    tailf:callpoint ConfdCliCommandAliasCallpoint;
      key name;
      tailf:info "Create command alias.";
      leaf name {
        type string;
        tailf:info "Name of the command alias. An alias name can be a single 
                    word or multiple words joined by a dash (-).";
      }
      leaf expansion {
        type string;
        mandatory true;
        tailf:info "Original command syntax. Valid abbreviations of the original 
                    command syntax can be entered for the command-syntax argument.";
      }
    }
    container session {
      uses session-params;
      tailf:info "User specific default CLI session parameters";
    }
  }
  
}
