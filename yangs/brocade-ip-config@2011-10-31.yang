/***********************************************************************
 * brocade-ip-config.yang: Brocade IP Forwarding data model.
 *
 * jusitnh
 *
 * Copyright (c) 2011 by Brocade Communications Systems, Inc.
 * All rights reserved.
 *
 **********************************************************************/

module brocade-ip-config {
    namespace "urn:brocade.com:mgmt:brocade-ip-config";
    prefix ip-config;

    import brocade-rbridge { prefix rbridge; }
    import brocade-interface { prefix interface;}
    import brocade-common-def {prefix common-def; }
    import brocade-intf-loopback {prefix intf-loopback; }
    import tailf-common { prefix tailf; }
      
    revision "2011-10-31" {
        description     
            "Initial version of this management module.";
    }         
	/*** TYPE DEFINITIONS ***/
	grouping phy-intf-ip-config {
		container ip-config {

            leaf mtu {
                type uint32 {
					range "576..9018" {
                    }
				}
                default 1500;
			}  

            leaf directed-broadcast {
                type empty;
            }

            leaf  proxy-arp{
                type empty;
            }

            leaf arp-aging-timeout {
                type uint32 {
                    range "0..240"{
					}
                }
                default 240;
            }

			list  address{
                ordered-by user;

                key "address";

                leaf address {
                    type common-def:ipv4-prefix-mask;
                }
				leaf  secondary {
					type empty;
			    } 
				leaf  ospf-passive {
					type empty;
			    } 
				leaf  ospf-ignore {
					type empty;
			    }
 
            }
		}
    }

	grouping intf-vlan-ip-config {
		container ip-config {

            leaf mtu {
                type uint32 {
					range "576..9018" {
                    }
				}
                default 1500;
			}  

            leaf directed-broadcast {
                type empty;
            }

            leaf  proxy-arp{
                type empty;
            }

            leaf arp-aging-timeout {
                type uint32 {
                    range "0..240"{
					}
                } 
                default 240;
                description
                    "Set arp age timeout value to interface 
                     (default value 240)";
            }

			list  address{
                ordered-by user;

                key "address";

                leaf address {
                    type common-def:ipv4-prefix-mask;
                }

				leaf  secondary {
					type empty;
			    } 
				leaf  ospf-passive {
                    type empty;
                }
                leaf  ospf-ignore {
                    type empty;
                }
            }
		}
    }

	grouping intf-po-ip-config {
		container ip-config {

            leaf mtu {
                type uint32 {
					range "576..9018" {
                    }
				}
                default 1500;
			}  

            leaf directed-broadcast {
                type empty;
            }

            leaf  proxy-arp{
                type empty;
            }

            leaf arp-aging-timeout {
                type uint32 {
                    range "0..35790"{
					}
                }
                default 240;
            }

			list  address{

                key "address";

                leaf address {
                    type common-def:ipv4-prefix-mask;
                }

				leaf  secondary {
					type empty;
			    } 
            }
		}
    }

    grouping loopback-intf-ip-config {
        container ip-config {

            list address {
                key "address";
                leaf address {
                    type intf-loopback:intf-loopback-ipv4addr-type;
                }
            }
        }
    }

	augment "/interface:interface/interface:tengigabitethernet/interface:ip" {
            	uses phy-intf-ip-config;
	}

	augment "/interface:interface/interface:fortygigabitethernet/interface:ip" {
            	uses phy-intf-ip-config;
	}

	augment "/interface:interface/interface:hundredgigabitethernet/interface:ip" {
            	uses phy-intf-ip-config;
	}

	augment "/interface:interface/interface:gigabitethernet/interface:ip" {
            	uses phy-intf-ip-config;
	}

    augment "/rbridge:rbridge-id/interface:interface/intf-loopback:loopback" {
        container ip {
            uses loopback-intf-ip-config;
        }
    }
    augment "/intf-loopback:hide-intf-loopback-holder/intf-loopback:interface/intf-loopback:loopback" {
        container ip {            
            uses loopback-intf-ip-config;
        }
    }

    augment "/rbridge:rbridge-id/interface:interface/interface:ve" {
        uses interface:interface-vrf-config;
        container ip {
            uses intf-vlan-ip-config;
        }
        leaf shutdown{
            type empty;
        }
    }

   	/*augment "/interface:interface-vlan/interface:interface/interface:ve" {
            leaf shutdown{
                type empty;
            }
    }

   	augment "/interface:interface-vlan/interface:interface/interface:ve/interface:ip" {
		uses intf-vlan-ip-config {
			refine "ip-config" {
			}
		}
    }*/

    augment "/interface:interface/interface:port-channel/interface:ip" {
    	container hide-ip-holder {
    		uses intf-po-ip-config;
        }
    }


}
