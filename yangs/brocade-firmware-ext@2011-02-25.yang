/***********************************************************************
 * brocade-firmware-ext.yang:Yang model for Firmware Information.
 *
 * August 2010, Platform Infrastructure team.
 *
 * Copyright (c) 2010-2011 by Brocade Communications Systems, Inc.
 * All rights reserved.
 **********************************************************************/
module brocade-firmware-ext {
    namespace "urn:brocade.com:mgmt:brocade-firmware-ext";
    prefix "firmware-extensions";


  import tailf-common {
    prefix tailf;
  }

  import brocade-common-def {
     prefix common-def;
  }
  import brocade-ras-ext { /* for switchidType */
   prefix "ras-extensions";
}

  organization
    "Brocade Communications Inc.";

  contact
    "Brocade Communications Systems, Inc.
     Postal: 130 Holger Way
             San Jose, CA 95134
             U.S.A
     Tel: +1-408-333-6061
     E-mail: support@Brocade.com
     web: www.brocade.com.";

  description
    "This sub module defines Firmware information.
     Copyright (c) 2010-2011 by Brocade Communications Systems, Inc.
     All rights reserved.";

  reference
    "";

  revision 2011-02-25 {
    description
      "Added new Action Point for Firmware info for Netconf interface.";
    reference
      "";
  }

  augment "/common-def:show" {
      container firmware {
        description "show firmwaredownload status";
        tailf:action firmwaredownloadstatus {
            input {
                leaf rbridge-id{
        			type ras-extensions:switchid-type;
                    mandatory false;
                }
                leaf brief {
                    type empty;
                    mandatory false;
                }
				leaf summary {
					type empty;
					mandatory false;
				}
				leaf logical-chassis {
					type empty;
					mandatory false;
				}
			}
            output {
                leaf result {
                    type string;
                }
            }
        }
		tailf:action firmwaredownloadhistory {
            input {
				leaf rbridge-id{
					type string {
						length 1..4 {
							error-message "Invalid rbridge-id (must be in the range <1..1023 or all>)";
						}
					}
					mandatory false;
				}
			}
			output {
				leaf result {
					type string;
				}
			}
		}
        tailf:action firmware {
            input {
                leaf auto-sync { 
                    type enumeration {
                        enum status {
                            value 0;
                        }
                    }

                }
            }
			output {
				leaf result {
					type string;
				}
			}
		}
        tailf:action version {
            input {
                leaf rbridge-id{
        			type ras-extensions:switchid-type;
                    mandatory false;
                }
                leaf brief {
                    type empty;
                    mandatory false;
                }
                leaf all-partitions {
                    type empty;
                    mandatory false;
                }
            }
            output {
                leaf result {
                    type string;
                }
            }
        }
        tailf:action firmware-features {
            input {
            }
            output {
                leaf result {
                    type string;
                }
            }
        }
    }
  }

  typedef node-type-enum {
      type enumeration {
          enum type-mm {
              value 0;
          }
          enum type-lc {
              value 2;
          }
      }
  }

  rpc show-firmware-version {
    description "conveys the firmware version info";
    input {
      leaf switchid {
        type ras-extensions:switchid-type;
        description
          "Switch id specifies the particular switch to fetch firmware
           version info.";
      }
    }
    output {
        list show-firmware-version {
            leaf switchid {
              type ras-extensions:switchid-type;
              description "Switch id specifies the particular switch to fetch firmware version info.";
            }
            leaf os-name {
              type string;
              description "Name of the Firmware version. Example: NOS, FOS etc."; 
            }
            leaf os-version {
              type string;
              description "Version of the Firmware.";
            }
            leaf copy-right-info {
              type string;
              description "Copy right information of the Firmware.";
            }
            leaf build-time {
              type string;
              description "Time information on the build of Firmware.";
            }
            leaf firmware-full-version {
              type string;
              description "Full version string of Firmware.";
            }
            leaf control-processor-vendor {
              type string;
              description "Information on the control processor.";
            }
            leaf control-processor-chipset {
              type string;
              description "Information on the control processor.";
            }
            leaf control-processor-memory {
              type string;
              description "Memory of the control processor.";
            }
            list node-info {
                leaf slot-no {
                    type uint32;
                }
                leaf node-instance-no {
                    type uint32;
                }
                leaf node-type {
                    type node-type-enum;
                }
                leaf is-active-cp {
                    type boolean;
                    mandatory false;
                }
                list firmware-version-info {
                    leaf application-name {
                        type string;
                        description "Name of the application.";
                    }
                    leaf primary-version {
                        type string;
                        description "Indicates the Primary version.";
                    }
                    leaf secondary-version {
                        type string;
                        description "Indicates the secondary version.";
                    }
                }
            }
        }
    }
  }
}
