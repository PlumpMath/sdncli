// YANG submodule for interface statedata definitions.
// Revisions:
//     2011-04-20: Initial version.
//

submodule interface-statedata 
{
    belongs-to netiron-statedata 
    {
        prefix "statedata";
    }

    import common-defs
    {
        prefix "common";
    }

    organization
        "Brocade Communications Inc.";

    contact
             "Technical Support Center"+
             "130 Holger Way,"+
             "San Jose, CA  95134"+
             "Email:  ipsupport@brocade.com"+
             "Phone: 1-800-752-8061"+
             "URL:  www.brocade.com";

    description "This module defines the device interface state data. VERSION: V5.8.00a";
    
    revision 2011-04-20
    {
        description "Initial revision";
    }

    grouping interface-statedata-grouping 
    {
        description "device interface state data group";
        container interface-statedata
        {
            description "List of interface configured on the system";
             
            list interface 
            {
                key interface-id;
                description "device interface state data";
                
                leaf interface-id
                {
                    type common:interface-all-types;
                    description "The interface identifier including chassis slot and port number";
                }

                choice link-state
                {
                    description "The state of the link";
                 
                    case up
                    {
                        leaf up
                        {
                            type empty;
                            description "The link is up";
                        }
                    }
                    case down
                    {
                        leaf down
                        {
                            type empty;
                            description "The link is down";
                        }
                    }
                    case empty
                    {
                        leaf empty
                        {
                            type empty;
                            description "The L2 state is empty";
                        }
                    }
                    case bpdu-disabled
                    {
                        leaf bpdu-disabled
                        {
                            type empty;
                            description "The L2 state is bpdu-disabled";
                        }
                    }
                    case disabled
                    {
                        leaf disabled
                        {
                            type empty;
                            description "The L2 state is disabled";
                        }
                    }
                } // end choice link-state

                choice l2-state
                {
                    description "The L2 state for the port";
                 
                    case disabled
                    {
                        leaf disabled
                        {
                            type empty;
                            description "The L2 state is disabled";
                        }
                    }
                    case blocked
                    {
                        leaf blocked
                        {
                            type empty;
                            description "The L2 state is blocked";
                        }
                    }
                    case listening
                    {
                        leaf listening
                        {
                            type empty;
                            description "The L2 state is listening";
                        }
                    }
                    case learning
                    {
                        leaf learning
                        {
                            type empty;
                            description "The L2 state is learning";
                        }
                    }
                    case preforwarding
                    {
                        leaf preforwarding
                        {
                            type empty;
                            description "The L2 state is preforwarding";
                        }
                    }
                    case forward
                    {
                        leaf forward
                        {
                            type empty;
                            description "The L2 state is forward";
                        }
                    }
                    case none
                    {
                        leaf none
                        {
                            type empty;
                            description "The L2 state is none";
                        }
                    }
                    case lk-disable
                    {
                        leaf lk-disable
                        {
                            type empty;
                            description "The L2 state is LK-DISABLE";
                        }
                    }
                    case oam-disable
                    {
                        leaf oam-disable
                        {
                            type empty;
                            description "The L2 state is OAM-DISABLE";
                        }
                    }
                    case dot1x-blocked
                    {
                        leaf dot1x-blocked
                        {
                            type empty;
                            description "The L2 state is DOT1X-BLOCKED";
                        }
                    }
                    case lacp-blocked
                    {
                        leaf lacp-blocked
                        {
                            type empty;
                            description "The L2 state is LACP-BLOCKED";
                        }
                    }
                    case chdlc-down
                    {
                        leaf chdlc-down
                        {
                            type empty;
                            description "The L2 state is cHDLC-DOWN";
                        }
                    }
                    case ppp-down
                    {
                        leaf ppp-down
                        {
                            type empty;
                            description "The L2 state is PPP-DOWN";
                        }
                    }
                    case inactive
                    {
                        leaf inactive
                        {
                            type empty;
                            description "The L2 state is inactive";
                        }
                    }
                    case na
                    {
                        leaf na
                        {
                            type empty;
                            description "The L2 state is N/A";
                        }
                    }
                } // end choice l2-state

                choice duplex
                {
                    description "The duplex mode of the interface";
                 
                    case half
                    {
                        leaf half
                        {
                            type empty;
                            description "Half Duplex";
                        }
                    }
                    case full
                    {
                        leaf full
                        {
                            type empty;
                            description "Full Duplex";
                        }
                    }
                    case none
                    {
                        leaf none
                        {
                            type empty;
                            description "None";
                        }
                    }
                    case na
                    {
                        leaf na
                        {
                            type empty;
                            description "N/A";
                        }
                    }
                } // end choice duplex

                leaf speed
                {
                    type string
                    {
                        length "1..6";
                    }
                    description "The bandwidth of the interface";
                }

                leaf trunk-id
                {
                    type string
                    {
                        length "1..6";
                    }
                    description "The trunk-id";
                }

                choice tag-mode
                {
                    description "The tag mode of the interface";
                 
                    case yes
                    {
                        leaf yes
                        {
                            type empty;
                            description "Yes";
                        }
                    }
                    case no
                    {
                        leaf no
                        {
                            type empty;
                            description "No";
                        }
                    }
                    case na
                    {
                        leaf na
                        {
                            type empty;
                            description "N/A";
                        }
                    }
                } // end choice tag-mode

                choice priority-level
                {
                    description "The priority level";
                 
                    case level0
                    {
                        leaf level0
                        {
                            type empty;
                            description "Level 0";
                        }
                    }
                    case level1
                    {
                        leaf level1
                        {
                            type empty;
                            description "Level 1";
                        }
                    }
                    case level2
                    {
                        leaf level2
                        {
                            type empty;
                            description "Level 2";
                        }
                    }
                    case level3
                    {
                        leaf level3
                        {
                            type empty;
                            description "Level 3";
                        }
                    }
                    case level4
                    {
                        leaf level4
                        {
                            type empty;
                            description "Level 4";
                        }
                    }
                    case level5
                    {
                        leaf level5
                        {
                            type empty;
                            description "Level 5";
                        }
                    }
                    case level6
                    {
                        leaf level6
                        {
                            type empty;
                            description "Level 6";
                        }
                    }
                    case level7
                    {
                        leaf level7
                        {
                            type empty;
                            description "Level 7";
                        }
                    }
                    case na
                    {
                        leaf na
                        {
                            type empty;
                            description "N/A";
                        }
                    }
                } // end choice l2-state

                leaf mac-address
                {
                    type common:mac_address;
                    description "The MAC address of the inteface";
                }

                leaf name
                {
                    type string
                    {
                        length "1..256";
                    }
                    description "The full port name of the interface";
                }

            } // end list interface

        } //end container interface-statedata
        
    } //end grouping interface-statedata-grouping
    
} //end submodule interface-statedata
