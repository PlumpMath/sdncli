/***********************************************************************
 * brocade-port-profile.yang: Brocade 'Automatic Migration of Port 
 *                            Profile' module.
 *
 *  Jul 2011, Pasupathi Duraiswamy , Sanjeev C Joshi 
 *
 * Copyright (c) 2011 by Brocade Communications Systems, Inc.
 * All rights reserved.
 *
 **********************************************************************/
module brocade-port-profile {
    namespace "urn:brocade.com:mgmt:brocade-port-profile";
    prefix "appm";

    import tailf-common {
        prefix tailf;
    }

    import brocade-common-def {
        prefix common-def;
    }
    
    import brocade-interface{
        prefix interface;
    }

    import brocade-mac-access-list {
        prefix mac-access-list;
    }

    import brocade-ip-access-list {
        prefix ip-access-list;
    }
    organization
        "Brocade Communications Systems, Inc.";

    contact           
        "Brocade Communications Systems, Inc.
         Postal: 130 Holger Way
                 San Jose, CA 95134
                  U.S.A
         Tel: +1-408-333-8000
         E-mail: support@Brocade.com 
         web: www.brocade.com.";

    description        
        "This management module is an instrumentation to manage  
        Automatic Port Profiles in the device.
        
        Glossary of the terms used:
        --------------------------- 
        APPM - Automatic Port Profile Management.
        AMPP - Automatic Migration of Port Profile.
        VM   - Virtual Machine.
        VAL  - Virtual Access Layer, provided by VCS.
        VCS  - Virtual Cluster Switching.
        
        
        A port-profile is a collection of network policies to be 
        applied on a network traffic on a given port.
        
        Automatic Migration of Port Profile (AMPP) functionality 
        provides fabric wide configuration of Ethernet policies and 
        achieves per port-profile forwarding and enables network level 
        features to support VM mobility.
        
        With Server Virtualization infrastructure, a VM can move from 
        one physical server to another. When such move occurs, it is 
        ideal for access-layer to apply the network policies on the 
        VM transparently. The Brocade VAL service provides such 
        automatic migration of the port-profile on a given VMAC 
        transparently. 
            
                                                   [Hypervisor2]
                                                    _____
                                                   |     |
                                                  /|VMAC |
                              '*************'    / |_____|
                              '             '   /     ^
                              '             '  /      |
                              '             '_/       ^
                              ' [VCS Fabric]'_        |
                              ' VMAC-PP map ' \     VM mobility
                              '             '  \      |
                              '             '   \     ^
                              '*************'    \  __|__
                                                  \|     |
                                                   |VMAC |
                                                   |_____|
                                                   [Hypervisor1]
                                                   
        This management module provides instrumentation to 
            - create/activate port-profile
            - map port-profile to MAC

        A Port-profile typically comprises of:
        +--------------------------------------------------------------+
        | sub-profile         Description                              |
        +--------------------------------------------------------------+
        | Vlan profile        Vlan membership and filtering rules.     |
        | QoS profile         Qos policies.                            |
        | FCoE profile        The attributes needed for the port to    |
        |                     support FCoE: FCoE VLAN, FCMAP, FCoE     |
        |                     Priority, Virtual Fabric ID etc.         |
        | Security profile    Security rules needed for the server     |
        |                     port, typically enabling 802.1x with EAP |
        |                     TLV extensions for VM Mobility, MAC based|
        |                     standard and extended ACLs.              |
        +--------------------------------------------------------------+
        
        VM MAC addresses are added to a port-profile to specify all the 
        network attributes for a server port. A port-profile is 
        activated on a server port when as part of regular MAC learning. 
        VM MAC to port-profile association is specified using this 
        management module. The actual association in hardware is applied
        when the MAC address is learned.";
        
    revision "2011-07-21" {
        description
            "Initial version of this management module.";
    }
    
	typedef port-profile-name-type {
		type common-def:name-string128;
	  	description
		  	"The name of the port-profile.";
	}

    typedef port-profile-domain-name-type {
        type common-def:name-string128;
        description
            "The name of the port-profile-domain.";
    }


    typedef appm-sw-mode-type{
        type enumeration {
            enum access {
                value 1;
                description 
                    "Set the layer2 interface to
                     access mode.";
            }
            enum trunk {
                value 2;
                description 
                    "Set the layer 2 interface to 
                     trunk mode.";
            }
        }
        description
            "The definition for specifying the mode of the L2 
            interface.'access' sets the layer2 interface to access
            mode and 'trunk' sets the layer2 interface to trunk
            mode.";
    }

    list port-profile {
        key name;
        description 
            "The list of port-profiles in the managed device. Each row
             represents port profile name and its subprofiles.";

        leaf name {
            type common-def:name-string128;
            description 
                "The name of the port-profile.";
            
        }
		container allow {
		description "Allow/Drop non-profiled macs";
     	   		leaf nonprofiledmacs {
                description "non-profiled macs";
                type empty;
        		}
        }
	
        container vlan-profile {
            presence true;
            description 
                "The Vlan profile.";
            
       }

        container fcoe-profile {
            presence true;
            description 
                "The FCoE profile.";
           }

        container qos-profile {
            presence true;
            description 
                "The QoS profile.";            

        }

       container security-profile {
            presence true;
            description 
                "The Security profile.";
        }
        
       container restrict-flooding-container {

           leaf restrict-flooding {
               type empty;
               description
                    "Restrict flooding";
            }
        }        
       }


    container port-profile-global {
        description
            "This provides the grouping for configuration parameters
             to activate and MAC for a port profile.";

        list port-profile {
            key name;
            description 
                "The list of automatic port profiles. Each row
                 provides the name of the port profile, indicates if the
                 profile is activated and the list of MAC addresses 
                 associated to the port profile.  ";

            leaf name {
                type common-def:name-string128;
                description
                    "The name of the port-profile.";
                
            }

            leaf activate {
                type empty;
                description 
                    "This specifies if this port-profile needs to be 
                    activated or not. The presence of this leaf 
                    indicates that this  profile is activated for 
                    profiling. Else, it is not activated.";
            }

            list static {
                key mac-address;
                description 
                    " The list of static VM macs associated to
                     port profile. Each row represents a MAC address
                     associated to the port profile.";

                leaf mac-address {
                    type mac-access-list:mac-address-type;
                    description
                        "This specifies the  MAC address for a 
                        port-profile identified by the value of the 
                        corresponding instance of 'port-profile/name'
                        can be mapped and applied.";
                }
                
            }        
        }
    }
   
    grouping port-profile-port-cmds {
        leaf port-profile-port {
            type empty;
            
                
            description 
                "This specifies if a physical/logical port can be 
                enabled for port-profiling. The presence of this 
                leaf indicates that the port is enabled for 
                port-profiling. Else, it is not enabled.
                
                Enabling a port for port-profiling results in to
                application of network policies (as per PP-MAC mapping)
                following MAC learning process.";
        }
    }
    
    grouping port-profile-port-association-cmds {

        container port-profile-to-interface-associations {
            
            container port-profile-port {

                container port-to-port-profile-domain-association {
                    description
                        "Associate a port-profile-domain with an interface.";
                    leaf profile-domain-name {
                        type port-profile-domain-name-type;
                        description
                            "The name of the port-profile-domain.";
                    }
                }
                
                list port-to-port-profile-associations {
                    key port-to-port-profile-association;
                    description 
                        "The list of automatic port profiles. Each row
                         provides the name of the port profile associated 
                         with an interface.";
                    
                    leaf port-to-port-profile-association {
                        type port-profile-name-type;
                        description
                            "The name of the port-profile.";
                    }
                }

            }

        }

    }

    grouping appm-allowed-vlan-cmds {
        container allowed {
                
            description 
                "A set of Vlan related configuration elements.";

            container vlan{
                description 
                    "This provides the grouping of all VLAN 
                     configuration elements for the port profile.";

                leaf all {
                    type empty;
                    description 
                        "This specifies whether all the VLANs should be
                         allowed to transmit or receive through the
                         Layer2 interface or not.

                         The presence of this leaf specifies that all 
                         the VLANs are allowed to 
                         transmit/receive through the layer 2
                         interface.";  
                }
                leaf none {
                    type empty;                
                    description 
                        "This specifies whether no vlan is allowed to
                         transmit or receive through the Layer 2 
                         interface or not.

                         The presence of this leaf specifies that no 
                         VLAN is allowed to transmit or
                         receive through the layer2 interface.";     
                }

                leaf add {
                    type interface:ui32-vlan-range;
                    description
                       "This specifies that only the VLANs or range of 
                        VLANs configured for this leaf are allowed to 
                        transmit or receive through the
                        layer 2 interface.";
                }
                
                leaf except {
                    type interface:ui32-vlan-range;
                    description 
                        "This specifies that all VLANs
                         except this VLAN range will be allowed to
                         transmit or receive through this 
                         Layer2 interface.";
                }

                leaf remove {
                    type interface:ui32-vlan-range;
                    description 
                        "This specifies that the specified VLAN range 
                         will be removed from the list of VLAN ranges
                         allowed to transmit or receive through this 
                         Layer2 interface.";
                }
            }
        }
    }


    grouping appm-trunk-vlan-classification {
        description
            "A set of elements defining the vlan access policy.";
            
        container trunk-vlan-classification {
            
            
            container allowed {
                description
                    "Set the VLANs that will Xmit/Rx through the Layer2
                    interface";
                    
                container vlan {
                    
                    list add {
                        key "trunk-vlan-id trunk-ctag-id";
                        
                        leaf trunk-vlan-id {
                            type interface:vlan-type;
                        }
                        
                        leaf trunk-ctag-id {
                            type interface:dot1q-vlan-type;
                        }
                    }
                    
                    list remove {
                        key "trunk-vlan-id trunk-ctag-id";
                        
                        leaf trunk-vlan-id {
                            type interface:vlan-type;
                        }
                        
                        leaf trunk-ctag-id {
                            type interface:dot1q-vlan-type;
                        }
                    }
                }
            }
        }
    }

    grouping appm-native-vlan-classification {
        
        container native-vlan-classification {
            
            leaf native-vlan-id {
                type uint32 {
                    range "4091..8191" {
                        description
                            "This specifies the range of values for
                            Vlan interface number.";
                    }
                }
            }
            
            leaf native-vlan-ctag-id {
                type interface:dot1q-vlan-type;
            }
        }
        
    }




    augment /port-profile/vlan-profile {

        container switchport-basic {
            leaf basic {
                type empty;
                description
                    "This specifies if the Layer 2 interface is in
                     basic Switching mode or not.

                     The presence of this leaf specifies that Ethernet
                     port acts as a basic Layer2 interface.";
            }
        }

        container switchport {
            //presence true;
            description 
                "This provides the grouping of all Switching character 
                 configuration elements of Layer 2 interface.";

            container mode {
                description 
                    "The mode of the Layer2 interface.";

                leaf vlan-mode {
                    type appm-sw-mode-type;
                    description 
                        " This specifies the mode of operation for
                         the Layer 2 ethernet port.";   
                }
            }

            container access{
                description 
                    "This specifies that the Layer 2 interface is in
                     access mode.";         
                container vlan {
                    description 
                        "This provides the grouping of Access VLAN 
                         configuration elements."; 

                   leaf name {
                       type interface:vlan-type;
                       description 
                            "This specifies the Interface VLAN number."; 
                    }
                }
            }
            
            
            container access-mac-vlan-classification {
                
                container access {
                    description
                        "The access layer characteristics of this
                         interface.";
                         
                    list vlan {
                        key "access-vlan-id access-mac-address";

                        leaf access-vlan-id {
                            type interface:vlan-type;
                            description
                                "Set the default VLAN for the interface";
                        }

                        leaf access-mac-address {
                            type interface:mac-address-type;
                            description
                                "Associate the Mac address with a vlan";
                        }
                    }
                }
            }

            container access-mac-group-vlan-classification {

                container access {
                    description
                        "The access layer characteristics of this
                         interface.";

                    list vlan {
                        key "access-vlan-id access-mac-group";

                        leaf access-vlan-id {
                            type interface:vlan-type;
                            description
                                "Set the default VLAN for the interface";
                        }

                        leaf access-mac-group {
                            type uint32;
                            description
                                "Associate a Mac group with a vlan";
                        }

                    }
                }
            }

            container trunk {
                uses appm-allowed-vlan-cmds;
                uses appm-trunk-vlan-classification;
                uses appm-native-vlan-classification;

                description 
                    "This specifies that Layer2 interface in
                     trunking mode.";

                leaf native-vlan {
                    type uint32 {
                        range "1..4090" {
                            description
                                "This specifies the range of values for
                                 Vlan interface number.";
                        }
                    }
                    description
                        "This specifies the native VLAN characteristics
                         of the Layer2 trunk interface for classifying
                         untagged traffic.";
                }

            }
        }
    }

    augment /port-profile/qos-profile {

        leaf cee {
            type common-def:name-string32;
            description 
                " This specifies QoS CEE Map for the port.";
        }
   
        container qos {
            description 
                "This provides the grouping of all Quality of Service 
                 parameters for the port.";

            leaf cos {
                type int32 {
                    range "0 .. 7" {
                        description 
                            "The Range of Default CoS value.";
                    }
                }
                default 0;
                description 
                    "This specifies the default Class of Service
                     (CoS).";
            }

            container trust {
                description 
                    "This specifies QoS Trust.";

                leaf trust-cos {
                    type empty;
                    description
                        "This specifies that trust L2 CoS field 
                         in incoming packets for 
                         deriving internal Traffic Class.";
                }
            }

            leaf cos-mutation {
                type common-def:name-string32;
                description 
                    "This specifies the CoS-t0-CoS mutation value.";
            }

            leaf cos-traffic-class {
                type common-def:name-string32;
                description 
                    "This specifies the mapping between Class of service
                     to Traffic class.";
            }

            container flowcontrol {
                description
                    "This provides the grouping of all flow control 
                     configuration elements.";      

                container flowcontrolglobal{

                    leaf tx {
                        type enumeration {
                            enum on {
                                value 1;
                                description
                                    "Enable Pause generation.";
                            }
                            enum off {
                                value 0;
                                description
                                    "Disable Pause generation.";
                            }
                        }
                        description
                            "This specifies if the pause generation is 
                             enabled or disabled.";
                    }

                    leaf rx {
                        type enumeration {
                            enum on {
                                value 1;
                                description
                                    "Enable Pause reception.";
                            }
                            enum off {
                                value 0;
                                description
                                    "Disable Pause reception";

                            }
                        }
                        description 
                            "This specifies if the Pause reception is
                             enabled or disabled.";
                    }


                }

                list pfc {
                    key pfc-cos;
                    description 
                        "The list of priority based flow control 
                         elements.Each row represents the Pfc Cos, 
                         Pause generation and reception values";

                    leaf pfc-cos {

                        type int32 {
                            range "0 .. 7" {
                                description
                                    "This specifies the range for CoS 
                                     Value.";   
                            }
                        }
                        description 
                            "This specifies the CoS value.";
                    }

                    leaf pfc-tx {
                        type enumeration {
                            enum on {
                                value 1;
                                description 
                                    "Enable pause generation.";
                            }
                            enum off {
                                value 0;
                                description 
                                    "Disable pause generation.";
                            }
                        }
                        mandatory true;
                        description  
                            "This specifies if the Pause generation is
                             enabled or disabled. 'on' enables the pause
                             generation and 'off' disables pause 
                             generation.";
                    }

                    leaf pfc-rx {
                        type enumeration {
                            enum on {
                                value 1;
                                description 
                                    "Enable pause reception.";
                            }
                            enum off {
                                value 0;
                                description 
                                    "Disable pause reception.";

                            }
                        }
                        mandatory true;
                        description 
                            "This specifies if the Pause reception is
                             enabled or disabled. 'on' enables the pause
                             reception and 'off' disables pause
                             reception."; 
                    }
                } 
            }
        }

    }

    augment /port-profile/fcoe-profile {
    
         container fcoeport {
            description 
                "The port associated with this port profile
                 will act as an FCOE port.";
        
            leaf fcoe-map-name {
                type string {
                    length "1..32" {
                        description 
                            "This specifies the range of characters 
                             that can be used for FCOE map name.";
                    }
                }
            }
        }
    }


    augment /port-profile/security-profile {
        container mac {
            description
                "This provides the grouping for MAC configuration
                 elements."; 
     
            container access-group {
                description 
                     "This provides the grouping of configuration
                      elements of MAC access list.";

                leaf access-group-name {
                    type mac-access-list:mac-acl-name;
                    description 
                        "This specifies the Access list name which is 
                         already configured at the global level. This
                         access list contains access rules.";
                }

                leaf in {
                    type empty;
                    description 
                        "This specifies if the direction is ingress or
                         not.
                         The presence of this leaf indicates Ingress 
                         direction.";
                }
            }
        }
        container ip {
            description
                "This provides the grouping for IP configuration
                 elements."; 
     
            container access-group {
                description 
                     "This provides the grouping of configuration
                      elements of IP access list.";

                leaf ipv4-access-group-name {
                    type ip-access-list:l3-acl-policy-name;
                    description 
                        "This specifies the Access list name which is 
                         already configured at the global level. This
                         access list contains access rules.";
                }

                leaf ipv4-in {
                    type empty;
                        description 
                        "This specifies if the direction is ingress or
                         not.
                         The presence of this leaf indicates Ingress 
                         direction.";
                }
            }
        }
        container ipv6 {
            description
                "This provides the grouping for ipV6 configuration
                 elements."; 
     
            container access-group {
                description 
                     "This provides the grouping of configuration
                      elements of IPv6 access list.";

                leaf ipv6-access-group-name {
                    type ip-access-list:l3-acl-policy-name;
                    description 
                        "This specifies the Access list name which is 
                         already configured at the global level. This
                         access list contains access rules.";
                }

                leaf ipv6-in {
                    type empty;
                      description 
                          "This specifies if the direction is ingress or
                           not.
                           The presence of this leaf indicates Ingress 
                           direction.";
                }
            }
        }
    }
    
    list port-profile-domain {
        key port-profile-domain-name;
        
        leaf port-profile-domain-name {
            type port-profile-domain-name-type;
        }

        list profile {
            key profile-name;

            leaf profile-name {
                type port-profile-name-type;
            }
        }
    }    


    augment "/interface:interface/interface:fortygigabitethernet" {
        uses port-profile-port-cmds;
        uses port-profile-port-association-cmds;
    }
    augment "/interface:interface/interface:hundredgigabitethernet" {
        uses port-profile-port-cmds;
        uses port-profile-port-association-cmds;
    }
    augment "/interface:interface/interface:tengigabitethernet" {
        uses port-profile-port-cmds;
        uses port-profile-port-association-cmds;
    }
    augment "/interface:interface/interface:gigabitethernet" {
        uses port-profile-port-cmds;
        uses port-profile-port-association-cmds;
    }
    
    augment "/interface:interface/interface:port-channel" {
        uses port-profile-port-cmds;
        uses port-profile-port-association-cmds {
            refine port-profile-to-interface-associations/port-profile-port/port-to-port-profile-associations {
            }
            refine port-profile-to-interface-associations/port-profile-port/port-to-port-profile-domain-association {
            }
        }
    }

}
