/***********************************************************************
 * brocade-license.yang: Brocade Licence Management data model
 *
 * July 2011, Vignesh Kumar, Murali Lachireddy, Dave Bhuyan
 *
 * Copyright (c) 2013 by Brocade Communications Systems, Inc.
 * All rights reserved.
 *
 **********************************************************************/

module brocade-license {
    namespace "urn:brocade.com:mgmt:brocade-license";
    prefix "brocade-license";


    import tailf-common {
        prefix tailf;
    }

    import brocade-interface {
        prefix interface;
    }

    import brocade-common-def {
        prefix common-def;
    }

    organization
        "Brocade Communications Inc.";

    contact
        "Brocade Communications Systems, Inc.
        Postal: 1745 Technology Drive,
        San Jose, CA 95110
        U.S.A
        Tel: +1-408-392-6061
        E-mail: support@Brocade.com
        web: www.brocade.com.";

    description
        "This management sub-module is an instrumentation to manage
        the licenses in the VCS fabric.

        Glossary of the terms used:
        ---------------------------
        DPOD        -   Dynamic ports on demand
        licStr      -   License string (i.e., license key)
        POD         -   Ports on demand

        ";

    revision 2011-08-22 {
        description
            "Providing Netconf Support to the existing version.";
    }

    typedef license-dpod-operation-type {
        type enumeration {
            enum release {
                value 1;
                description
                    "DPOD operation to release a license.";
            }
            enum reserve {
                value 2;
                description
                    "DPOD operation to reserve a license.";
            }
        }
    }

    /* define the "show license" functionality */
    augment "/common-def:show" {
        container license {
            tailf:action id {
                input {
                    choice single-or-all {
                        case rbridge-id {
                            leaf rbridge-id {
                                mandatory false;
                                type common-def:rbridge-id-all-type;
                            }
                        }
                        case all {
                            leaf all {
                                type empty;
                                description
                                    "License ID info for all switches
                                    in the fabric.";
                            }
                        }
                    }
                }
         
                output {
                    list licenseid-list {
                        key licenseid-rbridge-id;
                        leaf licenseid-rbridge-id {
                            type common-def:rbridge-id-type;
                            description
                                "Rbridge-id of switch to retrieve
                                license ID info from.";
                        }
                        leaf license-id {
                            type string;
                            description
                                "Indicates license Id.";
                        }
                    } /*licenseId-list */
                } /* end of output */
            } /* end of licenseidshow */
        } /* end of license container */

        container enh-show-license-keys {
            tailf:action license {
                input {
                    choice single-or-all {
                        case rbridge-id {
                            leaf rbridge-id {
                                mandatory false;
                                type common-def:rbridge-id-all-type;
                            }
                        }
                        case all {
                            leaf all {
                                type empty;
                                description
                                    "License Key info for all switches
                                    in the fabric.";
                            }
                        }
                    }
                }
                output {
                    list license-list {
                        key license-rbridge-id;
                        leaf license-rbridge-id {
                            type common-def:rbridge-id-type;
                            description
                                "Rbridge-id of switch to retrieve
                                license key info from.";
                        }
                        list license-details {
                            leaf license-data {
                                type string;
                                description
                                    "Indicates license data.";
                            }
                            leaf license-expiry-date {
                                type string;
                                description
                                    "Indicates license expiry date
                                    information.";
                            }
                            leaf license-feature-name {
                                type string;
                                description
                                    "Indicates license feature name.";
                            }
                            leaf license-capacity {
                                type string;
                                description
                                    "Indicates license capacity.";
                            }
                            leaf license-consumed {
                                type string;
                                description
                                    "Indicates license consumed.";
                            }
                            leaf license-valid-state {
                                type string;
                                description
                                    "Indicates license validity state.";
                            }
                        } /*license-details */
                    } /*license-list */
                } /* output */
            } /* licenseshow */
            tailf:action dpod {
                input {
                    choice single-or-all {
                        case rbridge-id {
                            leaf rbridge-id {
                                mandatory false;
                                type common-def:rbridge-id-all-type;
                            }
                        }
                        case all {
                            leaf all {
                                type empty;
                                description
                                    "DPOD info for all switches
                                    in the fabric.";
                            }
                        }
                    }
                }
                
                output {
                    list showdpod-list {
                        key showdpod-rbridge-id;
                        leaf showdpod-rbridge-id {
                            type common-def:rbridge-id-type;
                            description
                                "Rbridge-id of switch to retrieve
                                DPOD info from";
                        }
                        list dpod-details {
                            leaf dpod-ports {
                                type uint32;
                                description
                                    "Indicates number of DPOD ports
                                    available in this switch.";
                            }
                            leaf dpod-licenses-installed {
                                type uint32;
                                description
                                    "Indicates number of POD licenses
                                    installed.";
                            }
                            leaf num-ports-provisioned {
                                type uint32;
                                description
                                    "Indicates port assignments
                                    provisioned for use in this
                                    switch.";
                            }
                            leaf num-ports-reserved {
                                type uint32;
                                description
                                    "Indicates ports assigned to
                                    installed licenses.";
                            }
                            leaf num-ports-license-available {
                                type uint32;
                                description
                                    "Indicates license reservations
                                    are still available for use by
                                    unassigned ports.";
                            }
                        } /*dpod-details */
                    } /*showdpod-list */
                } /* output */
            } /* licensepodshow */
        } /* end of licensekeys container */

    } /* end of show */

    /* define the "license operations" functionality */
    container license {
        description
            "The function for installing or uninstalling the license
            keys of a given RBridge.";
        tailf:action add {
            input {
                choice str-file {
                    case licStr {
                        leaf licStr {				
                    		type string {
                        		length 1..256;
                    		}
                    		mandatory true;
                    		description
                        		"License string";
                		}
                    }
                	case FTP-URL {
                        leaf FTP-URL {
                    		type string {
                        		length 1..256;
                    		}
                    		mandatory true;
                    		description 
                        		"FTP path for License file";
                		}
                    }
                	case SCP-URL {
                        leaf SCP-URL {
                    		type string {
                        		length 1..256;
                    		}
                    		mandatory true;
                    		description
                        		"SCP path for License file";
                		}
                    }
                }
                leaf rbridge-id {
                    type common-def:rbridge-id-type;
                    description
                        "Rbridge-id of switch to add
                        license key to";
                }
            }
        } /* license add */

        tailf:action remove {
            input {
                leaf licStr {
                    type common-def:feature-type;
                    mandatory true;
                    description
                        "Specifies the feature name or license string.";
                }
                leaf rbridge-id {
                    type common-def:rbridge-id-type;
                    description
                        "Rbridge-id of switch to remove
                        license key from.";
                }
            }
        } /* license remove */
    } /* end of license container */

    /* define the "license DPOD CallPoint" functionality */
    container dpod {
        list port-id {
            ordered-by user;
            key port-id;
            leaf port-id {
                type interface:interface-type;
                mandatory true;
                description
                    "Port details for identification
                    [rbridge-id/slot/port].";
            }

            leaf operation {
                type license-dpod-operation-type;
                description
                    "Operation to release or reserve a DPOD
                    license for this port.";
            }

        } /* end of list */
    } /* dpod container */

} /* end of license submodule */
