module vyatta-system-acm {
	namespace "urn:vyatta.com:mgmt:vyatta-system-acm";
	prefix system-acm;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-26 {
		description "Initial revision.";
		configd:migration 1;
	}

	augment /system:system {
		container acm {
			presence "true";
			configd:help "Access Control Management";
			configd:end "/opt/vyatta/share/tmplscripts/system/acm/configd_end.sh";
		}
	}
}
