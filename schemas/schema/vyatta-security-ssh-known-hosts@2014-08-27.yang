module vyatta-security-ssh-known-hosts {
	namespace "urn:vyatta.com:mgmt:vyatta-ssh-known-hosts";
	prefix security-ssh-known-hosts;

	import vyatta-security {
		prefix security;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /security:security {
		container ssh-known-hosts {
			presence "true";
			configd:help "SSH known, trusted hosts";
			configd:end "/opt/vyatta/share/tmplscripts/security/ssh-known-hosts/configd_end.sh";
			list host {
				configd:help "Host name or IP of remote trusted host";
				configd:validate "/opt/vyatta/share/tmplscripts/security/ssh-known-hosts/host/configd_validate1.cli";
				key "tagnode";
				leaf tagnode {
					type string;
					configd:help "Host name or IP of remote trusted host";
				}
				leaf key {
					type string {
						configd:syntax "/opt/vyatta/share/tmplscripts/security/ssh-known-hosts/host/key/configd_syntax1.cli";
					}
					configd:help "Public key for host";
				}
				leaf load-from-file {
					type string;
					configd:help "Load public key from file";
					configd:subst "/opt/vyatta/share/tmplscripts/security/ssh-known-hosts/host/load-from-file/configd_subst1.cli";
				}
				leaf fetch-from-server {
					type empty;
					configd:help "Query remote server for public key";
					configd:subst "/opt/vyatta/share/tmplscripts/security/ssh-known-hosts/host/fetch-from-server/configd_subst1.cli";
				}
			}
		}
	}
}
