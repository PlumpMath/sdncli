module vyatta-system-login-sssd {
	namespace "urn:vyatta.com:mgmt:vyatta-system-login-sssd";
	prefix system-login-sssd;

	import vyatta-system {
		prefix system;
	}
	import vyatta-system-login {
		prefix system-login;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-12-17 {
		description "Initial revision.";
	}


	augment /system:system/system-login:login {
		container auth-chain {
			configd:help "Authentication chain";
			leaf-list method {
				configd:help "Authentication method";
				type enumeration {
					enum "tacplus" {
						configd:help "TACACS+ authentication";
					}
					enum "local" {
						configd:help "Local authentication";
					}
				}
			}
		}
	}
}
