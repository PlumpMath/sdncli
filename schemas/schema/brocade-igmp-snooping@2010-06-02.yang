/***********************************************************************
 * brocade-igmp-snooping.yang : Brocade IGMP Snooping data model
 *
 * June 2010, Anish Bhaskaran
 *
 * Copyright (c) 2010 by Brocade Communications Systems, Inc.
 * All rights reserved.
 *
 **********************************************************************/

module brocade-igmp-snooping {
    namespace "urn:brocade.com:mgmt:brocade-igmp-snooping";
    prefix "igmp-snooping";
	
    import tailf-common { prefix "tailf"; }
    import ietf-inet-types  { prefix "inet"; }
   
    import brocade-interface {
        prefix interface;
    }

    organization
        "Brocade Communications Systems, Inc.";
    
    contact           
        "Brocade Communications Systems, Inc.
         Postal: 1745 Technology Drive,
                 San Jose, CA 95110 
                  U.S.A
         Tel: +1-408-392-6061
         E-mail: support@Brocade.com 
         web: www.brocade.com.";
         
    description      
        "This management module is an instrumentation to manage the 
        'Internet Group Management Protocol (IGMP) Snooping'.";
        
    revision "2010-06-02" {
        description     
            "Initial version of this module.";
    }         

	/* Module Definition */
      container igmp-snooping {
             container ip {

		container igmp {

			container snooping {

				leaf enable {
					type empty;
				}

			/*	leaf restrict-unknown-mcast {
					type empty;
				}*/
			}
		}
	}
   }

    typedef lmqt-type {
        type uint32 {
            range "100..25500";
        }
    }

    typedef qi-type {
		type uint32 {
			range "1..18000";
		}
    }

    typedef qmrt-type {
		type uint32 {
			range "1..25";
		}
    }

    typedef mrti-type {
		type uint32 {
			range "1..60000";
		}
    }

    typedef string-type {
        type string {
			length "1..10";
		}
    }

	augment "/interface:interface-vlan/interface:interface/interface:vlan/interface:ip" {
		description "Internet Protocol (IP)";

		container igmp {

			leaf last-member-query-interval {
				type lmqt-type;
                units "milliSeconds";
                default 1000;
			}

			leaf query-interval {
				type qi-type;
                units "Seconds";
                default 125;
			}

			leaf query-max-response-time {
                type qmrt-type;
                units "Seconds";
                default 10;
			}

			container snooping {

				leaf enable {
                      
					type empty;
				}

				leaf fast-leave {
					type empty;
				}

				leaf mrouter-timeout {
                    type mrti-type;
                    units "Seconds";
                    default 300;
				}

               leaf restrict-unknown-multicast {
                    type empty;
                }

				container querier {

					leaf qenable {
						type empty;
					}
				}

				container mrouter {

					list interface {
						
						key "if-type value";

						leaf if-type {
							type enumeration {
								enum GigabitEthernet {
								}
								enum TenGigabitEthernet {
								}
								enum FortyGigabitEthernet {
								}
								enum Port-channel {
								}
								enum HundredGigabitEthernet {
								}
							}
						}

						leaf value {
							type string-type;
						}
					}
				}
			}

			list static-group {

				key "mcast-address interface if-type value";

				leaf mcast-address {
					type inet:ipv4-address;
				}

				leaf interface {
					type enumeration {
						enum interface {
						}
					}
				}

				leaf if-type {
					type enumeration {
						enum GigabitEthernet {
						}
						enum TenGigabitEthernet {
						}
						enum FortyGigabitEthernet {
						}
						enum Port-channel {
						}
						enum HundredGigabitEthernet {
						}
					}
				}

				leaf value {
                    type string-type;
				}
			}
		}
	}
}
