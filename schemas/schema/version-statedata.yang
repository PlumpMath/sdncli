// YANG submodule for version statedata defintions.
// Revisions:
//     2011-04-20: Initial version.
//

submodule version-statedata
{
    belongs-to netiron-statedata
    {
        prefix "statedata";
    }

    import common-defs
    {
        prefix "common";
    }

    organization
        "Brocade Communications Inc.";

    contact
             "Technical Support Center"+
             "130 Holger Way,"+
             "San Jose, CA  95134"+
             "Email:  ipsupport@brocade.com"+
             "Phone: 1-800-752-8061"+
             "URL:  www.brocade.com";

    description "This module defines the device version state data. VERSION: V5.8.00a";
    
    revision 2011-04-20
    {
        description "Initial revision";
    }


    grouping device-id-grouping
    {
        leaf serial
        {
            type string
            {
                length 1..20;
            }
            description "device serial number";
        }

        leaf part
        {
            type string
            {
                length 1..20;
            }
            description "device part number";
        }
    }

    grouping software-version-grouping
    {
        leaf version
        {
            type string
            {
                length 1..127;
            }
            description "Image version.";
        }

        leaf compiled-on
        {
            type string
            {
                length 1..127;
            }
            description "The image compilation date and time.";
        }

        leaf label
        {
            type string
            {
                length 1..15;
            }
            description "The image label..";
        }

        leaf length
        {
            type uint32
            {
                range "0..4294967295";
            }
            description "The image length.";
        }

        leaf source
        {
            type string
            {
                length 1..63;
            }
            description "The boot source";
        }
    }

    grouping flash-grouping
    {
        leaf flash-size
        {
            type uint32
            {
                range "0..4294967295";
            }
            description "The flash size.";
        }

        leaf flash-name
        {
            type string
            {
                length "1..31";
            }
            description "The flash name.";
        }
    }

    grouping license-grouping
    {
        description "Software License Id";
        leaf software-packaging-type
        {
            type string
            {
                length 1..31;
            }
            description "Software Packaging Type";
        }
        leaf license-id
        {
            type string
            {
                        length 1..11;
            }
            description "device license identifier";
        }
    }

    grouping version-statedata-grouping
    {
        description "device version state data";
        container version-statedata
        {
            leaf system
            {
                type string
                {
                    length 1..127;
                }
                description "System model/product/chassis type";
            }

            leaf chassis-mode
            {
                type string
                {
                    length 1..16;
                }
                description "Chassis mode (XMR/MLX)";
            }

            container system-id
            {
                description "System Identifier";
                uses device-id-grouping;
            }

            container factory-id
            {
                description "System Factory Identifier";
                uses device-id-grouping;
            }

            container license
            {
                description "Software License Id";
                uses license-grouping;
            }

            leaf cpld-version
            {
                type uint8
                {
                    range "0..255";
                }
                description "The CPLD Version.";
            }

            leaf micro-controller-version
            {
                type uint8
                {
                    range "0..255";
                }
                description "The Micro Controller Version.";
            }

            leaf pbif-version
            {
                type uint8
                {
                    range "0..255";
                }
                description "The PBIF Version. (0 = not ready)";
            }

            container daughter-board-id
            {
                description "Daughter Board";
                uses device-id-grouping;
            }

            list module
            {
                key "module-name";
                description "The module name (CER has only 1 module).";
                leaf module-name
                {
                    type string
                    {
                        length 1..256;
                    }
                    description "Module name";
                }

                leaf module-state
                {
                    type string
                    {
                        length 1..16;
                    }
                    description "Module state (if down)";
                }

                container module-id
                {
                    description "Module Identifier";
                    uses device-id-grouping;
                }

                list fe
                {
                    key "fe-id";
                    description "The FE";
                    leaf fe-id
                    {
                        type uint8
                        {
                            range 1..16;
                        }
                        description "FE id";
                    }
                    leaf fe-type
                    {
                        type uint32
                        {
                            range 1..1048575;
                        }
                        description "FE type";
                    }

                    leaf fe-ver
                    {
                        type uint8
                        {
                            range 1..16;
                        }
                        description "FE version";
                    }
                }

                container module-license
                {
                    description "Software License Id";
                    uses license-grouping;
                }

                container software-version
                {
                    description "Software Versions";
                    container boot
                    {
                        description "Boot Image Software Versions";
                        uses software-version-grouping;
                    }
                    container monitor
                    {
                        description "Monitor Image Software Versions";
                        uses software-version-grouping;
                    }
                    container ironware
                    {
                        description "Ironware Image Software Versions";
                        uses software-version-grouping;
                    }
                }

                leaf fpga-versions
                {
                    type string
                    {
                        length "0..255";
                    }
                    description "The FPGA Versions.";
                }
 
                container mac-string-container
                {
                    description "MAC string container";
                    leaf-list mac-string-list
                    {
                        description "The MAC string.";
                        type string
                        {
                            length "1..15";
                        }
                    }
                }
 
                container processor
                {
                    leaf processor-speed
                    {
                        type uint32
                        {
                            range "0..4294967295";
                        }
                        description "The Processor Speed (MHz)";
                    }
    
                    leaf processor-type
                    {
                        type string
                        {
                            length "1..5";
                        }
                        description "Processor Type";
                    }
    
                    leaf processor-revision
                    {
                        type uint32
                        {
                            range "0..4294967295";
                        }
                        description "Processor revision";
                    }
    
                    leaf bus-speed
                    {
                        type uint32
                        {
                            range "0..4294967295";
                        }
                        description "The Bus Speed (MHz)";
                    }
                }
    
                container boot-flash
                {
                    description "Boot Flash";
                    uses flash-grouping;
                }
    
                container code-flash
                {
                    description "Code Flash";
                    uses flash-grouping;
                }
    
                leaf dram-size
                {
                    type uint32
                    {
                        range "0..4294967295";
                    }
                    description "The DRAM size.";
                }
    
                leaf sram-size
                {
                    type uint32
                    {
                        range "0..4294967295";
                    }
                    description "The SRAM size.";
                }
    
                leaf bram-size
                {
                    type uint32
                    {
                        range "0..4294967295";
                    }
                    description "The BRAM size.";
                }

                container dma-container
                {
                    description "DMA information container.";
                    list dma-list
                    {
                        key "ppcr-id";
                        description "The DMA information container.";
                        leaf ppcr-id
                        {
                            type uint32
                            {
                                range "0..4294967295";
                            }
                            description "The PPCR Id.";
                        }
                        leaf cam-size
                        {
                            type uint32
                            {
                                range "0..4294967295";
                            }
                            description "The CAM size (K entries)";
                        }
                        leaf pram-size
                        {
                            type uint32
                            {
                                range "0..4294967295";
                            }
                            description "The PRAM size (K entries)";
                        }
                        leaf age-ram-size
                        {
                            type uint32
                            {
                                range "0..4294967295";
                            }
                            description "The AGE RAM size (K entries)";
                        }
                    }
                }
    
                leaf system-uptime
                {
                    type string
                    {
                        length "1..63";
                    }
                    description "System Uptime";
                }
            }
        }
    }
}
