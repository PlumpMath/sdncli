module vyatta-security-firewall {
	namespace "urn:vyatta.com:mgmt:vyatta-security-firewall";
	prefix security-firewall;

	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-openvpn {
		prefix interfaces-openvpn;
	}
	import vyatta-interfaces-tunnel {
		prefix interfaces-tunnel;
	}
	import vyatta-interfaces-vti {
		prefix interfaces-vti;
	}
	import vyatta-security {
		prefix security;
	}
	import configd {
		prefix configd;
	}

	organization "Brocade Communications Systems, Inc.";
	contact
		"Brocade Communications Systems, Inc.
		 Postal: 130 Holger Way
			 San Jose, CA 95134
		 E-mail: support@Brocade.com
		 Web: www.brocade.com";

	revision 2014-11-07 {
		description "Update for 3.2.1R2";
	}
	
	revision 2014-10-28 {
		description "Update for 3.2.1R1";
	}
	
	revision 2014-08-27 {
		description "Initial revision.";
		configd:migration 1;
	}

	typedef bandwidth-suffix {
		type string {	/* Number followed by suffix */
			pattern '[0-9]+(\.([0-9]+))?(([KMBGTkmgt][iI]?)?(bit|bps))?';
			configd:pattern-help "<number><suffix>";
		}
	}

	grouping marking {
		container mark {
			configd:help "Packet marking action";
			leaf dscp {
				type uint8 {
					range 0..63;
				}
				configd:help "DSCP value to be marked";
			}
			leaf pcp {
				type uint8 {
					range 0..7;
				}
				configd:help "802.1 priority code point to apply";
			}
		}
	}

	augment /security:security {
		container firewall {
			presence "true";
			configd:priority "310";
			configd:help "Firewall";
			configd:begin "/opt/vyatta/share/tmplscripts/security/firewall/configd_begin.sh";
			configd:end "/opt/vyatta/share/tmplscripts/security/firewall/configd_end.sh";
			leaf tcp-strict {
				type empty;
				configd:help "Enable tcp strict stateful firewall rule";
				configd:create "/opt/vyatta/share/tmplscripts/security/firewall/tcp-strict/configd_create.sh";
				configd:delete "/opt/vyatta/share/tmplscripts/security/firewall/tcp-strict/configd_delete.sh";
				configd:end "/opt/vyatta/share/tmplscripts/security/firewall/tcp-strict/configd_end.sh";
			}
			leaf broadcast-ping {
				type enumeration {
					enum "enable";
					enum "disable";
				}
				configd:help "Policy for handling broadcast IPv4 ICMP echo requests";
				default "disable";
				configd:update "/opt/vyatta/share/tmplscripts/security/firewall/broadcast-ping/configd_update.sh";
				configd:delete "/opt/vyatta/share/tmplscripts/security/firewall/broadcast-ping/configd_delete.sh";
			}
			leaf all-ping {
				type enumeration {
					enum "enable";
					enum "disable";
				}
				configd:help "Policy for handling of all IPv4 ICMP echo requests";
				default "enable";
				configd:update "/opt/vyatta/share/tmplscripts/security/firewall/all-ping/configd_update.sh";
				configd:delete "/opt/vyatta/share/tmplscripts/security/firewall/all-ping/configd_delete.sh";
			}
			leaf syn-cookies {
				type enumeration {
					enum "enable";
					enum "disable";
				}
				configd:help "Policy for using TCP SYN cookies with IPv4";
				configd:update "/opt/vyatta/share/tmplscripts/security/firewall/syn-cookies/configd_update.sh";
				configd:delete "/opt/vyatta/share/tmplscripts/security/firewall/syn-cookies/configd_delete.sh";
			}
			list name {
				configd:help "Firewall group";
				configd:delete "/opt/vyatta/share/tmplscripts/security/firewall/name/configd_delete.sh";
				configd:end "/opt/vyatta/share/tmplscripts/security/firewall/name/configd_end.sh";
				key "tagnode";
				leaf tagnode {
					type string {
						pattern "[0-9A-Za-z][-_0-9A-Za-z]*" {
							error-message "only alpha-numeric policy name allowed";
						}
					}
					configd:help "Firewall group";
				}
				leaf description {
					type string;
					configd:help "Rule-set description";
				}
				list rule {
					configd:help "Rule number (1-9999)";
					configd:validate "/opt/vyatta/share/tmplscripts/security/firewall/name/rule/configd_validate1.cli";
					key "tagnode";
					leaf tagnode {
						type uint32 {
							range 1..9999;
						}
						configd:help "Rule number (1-9999)";
					}
					container tcp {
						presence "true";
						configd:help "TCP flags to match";
						configd:validate "/opt/vyatta/share/tmplscripts/security/firewall/name/rule/tcp/configd_validate1.cli";
						leaf flags {
							type string {
								pattern "(((!?(SYN|ACK|FIN|RST|PSH|URG),)*(!?(SYN|ACK|FIN|RST|PSH|URG))))" {
									error-message "Invalid value for TCP flags. Allowed values : SYN ACK FIN RST URG PSH
When specifying more than one flag, flags should be comma-separated.
For example : value of 'SYN,!ACK,!FIN,!RST' will only match packets with
the SYN flag set, and the ACK, FIN and RST flags unset";
								}
							}
							configd:help "TCP flags to match";
							configd:comp_help "/opt/vyatta/share/tmplscripts/security/firewall/name/rule/tcp/flags/configd_comp_help.txt";
						}
					}
					container ipv6-route {
						presence "true";
						configd:help "IPv6 route";
						configd:validate "/opt/vyatta/share/tmplscripts/security/firewall/name/rule/ipv6-route/configd_validate1.cli";
						leaf type {
							type uint8 {
								range 0..255;
							}
							configd:help "IPv6 route type must be between 0 and 255";
						}
					}
					container icmp {
						presence "true";
						configd:help "ICMP for IPV4";
						configd:validate "/opt/vyatta/share/tmplscripts/security/firewall/name/rule/icmp/configd_validate1.cli";
						leaf type-name {
							type string {
								configd:syntax "/opt/vyatta/share/tmplscripts/security/firewall/name/rule/icmp/type-name/configd_syntax1.cli";
							}
							configd:help "ICMP type-name";
							configd:allowed "/opt/vyatta/share/tmplscripts/security/firewall/name/rule/icmp/type-name/configd_allowed.sh";
						}
						leaf code {
							type uint8 {
								range 0..255;
							}
							configd:help "ICMP code must be between 0 and 255";
							configd:validate "/opt/vyatta/share/tmplscripts/security/firewall/name/rule/icmp/code/configd_validate1.cli";
							configd:validate "/opt/vyatta/share/tmplscripts/security/firewall/name/rule/icmp/code/configd_validate2.cli";
						}
						leaf type {
							type uint8 {
								range 0..255;
							}
							configd:help "ICMP type must be between 0 and 255";
							configd:validate "/opt/vyatta/share/tmplscripts/security/firewall/name/rule/icmp/type/configd_validate1.cli";
							configd:validate "/opt/vyatta/share/tmplscripts/security/firewall/name/rule/icmp/type/configd_validate2.cli";
						}
					}
					leaf description {
						type string;
						configd:help "Rule description";
					}
					leaf action {
						type enumeration {
							enum "accept";
							enum "drop";
						}
						configd:help "Rule action";
					}
					uses marking;

					leaf disable {
						type empty;
						configd:help "Disable firewall rule";
						configd:create "/opt/vyatta/share/tmplscripts/security/firewall/name/rule/disable/configd_create.sh";
						configd:delete "/opt/vyatta/share/tmplscripts/security/firewall/name/rule/disable/configd_delete.sh";
					}
					leaf pcp {
						type uint8 {
							range 0..7;
						}
						configd:help "802.1 priority code point to match (0 to 7)";
					}
					container police {
						configd:help "Packet rate limiting";
						configd:validate "/opt/vyatta/share/tmplscripts/security/firewall/name/rule/police/configd_validate.cli";
						leaf bandwidth {
							type bandwidth-suffix;
							configd:help "Bandwidth limit";
						}
						leaf burst {
							type uint32 {
								range 1..312500000;
							}
							configd:help "Burst size in bytes";
						}
						container then {
							configd:help "Result for packets over police limit";
							leaf action {
								type enumeration {
									enum "drop" {
										configd:help "Drop if overlimit";
									}
									enum "accept" {
										configd:help "Accept if overlimit";
									}
								}
								configd:help "Police action";
							}
							uses marking;
						}
					}
					leaf fragment {
						type empty;
						configd:help "Match on fragmented packets";
					}
					container icmpv6 {
						presence "true";
						configd:help "ICMP for IPV6";
						configd:validate "/opt/vyatta/share/tmplscripts/security/firewall/name/rule/icmpv6/configd_validate1.cli";
						leaf type-name {
							type string {
								configd:syntax "/opt/vyatta/share/tmplscripts/security/firewall/name/rule/icmpv6/type-name/configd_syntax1.cli";
							}
							configd:help "ICMPv6 type/code names";
							configd:allowed "/opt/vyatta/share/tmplscripts/security/firewall/name/rule/icmpv6/type-name/configd_allowed.sh";
						}
						leaf code {
							type uint8 {
								range 0..255;
							}
							configd:help "ICMP code must be between 0 and 255";
							configd:validate "/opt/vyatta/share/tmplscripts/security/firewall/name/rule/icmpv6/code/configd_validate1.cli";
							configd:validate "/opt/vyatta/share/tmplscripts/security/firewall/name/rule/icmpv6/code/configd_validate2.cli";
						}
						leaf type {
							type uint8 {
								range 0..255;
							}
							configd:help "ICMP type must be between 0 and 255";
							configd:validate "/opt/vyatta/share/tmplscripts/security/firewall/name/rule/icmpv6/type/configd_validate1.cli";
							configd:validate "/opt/vyatta/share/tmplscripts/security/firewall/name/rule/icmpv6/type/configd_validate2.cli";
						}
					}
					container source {
						presence "true";
						configd:help "Source parameters";
						leaf mac-address {
							type string {
								configd:syntax "/opt/vyatta/share/tmplscripts/security/firewall/name/rule/source/mac-address/configd_syntax1.cli";
							}
							configd:help "Source MAC address";
							configd:validate "/opt/vyatta/share/tmplscripts/security/firewall/name/rule/source/mac-address/configd_validate1.cli";
							configd:validate "/opt/vyatta/share/tmplscripts/security/firewall/name/rule/source/mac-address/configd_validate2.cli";
						}
						leaf address {
							type string {
								configd:syntax "/opt/vyatta/share/tmplscripts/security/firewall/name/rule/source/address/configd_syntax1.cli";
								configd:syntax "/opt/vyatta/share/tmplscripts/security/firewall/name/rule/source/address/configd_syntax2.cli";
							}
							configd:help "Source IP address, subnet, or address-group";
							configd:allowed "/opt/vyatta/share/tmplscripts/security/firewall/name/rule/source/address/configd_allowed.sh";
							configd:validate "/opt/vyatta/share/tmplscripts/security/firewall/name/rule/source/address/configd_validate1.cli";
							configd:validate "/opt/vyatta/share/tmplscripts/security/firewall/name/rule/source/address/configd_validate2.cli";
							configd:validate "/opt/vyatta/share/tmplscripts/security/firewall/name/rule/source/address/configd_validate3.cli";
							configd:validate "/opt/vyatta/share/tmplscripts/security/firewall/name/rule/source/address/configd_validate4.cli";
							configd:validate "/opt/vyatta/share/tmplscripts/security/firewall/name/rule/source/address/configd_validate5.cli";
							configd:validate "/opt/vyatta/share/tmplscripts/security/firewall/name/rule/source/address/configd_validate6.cli";
						}
						leaf port {
							type string;
							configd:help "Source port or port-group";
							configd:allowed "/opt/vyatta/share/tmplscripts/security/firewall/name/rule/source/port/configd_allowed.sh";
							configd:validate "/opt/vyatta/share/tmplscripts/security/firewall/name/rule/source/port/configd_validate1.cli";
							configd:validate "/opt/vyatta/share/tmplscripts/security/firewall/name/rule/source/port/configd_validate2.cli";
						}
					}
					leaf log {
						type empty;
						configd:help "Enable logging for Firewall rule";
					}
					container destination {
						presence "true";
						configd:help "Destination parameters";
						leaf mac-address {
							type string {
								configd:syntax "/opt/vyatta/share/tmplscripts/security/firewall/name/rule/destination/mac-address/configd_syntax1.cli";
							}
							configd:help "Destination MAC address";
							configd:validate "/opt/vyatta/share/tmplscripts/security/firewall/name/rule/destination/mac-address/configd_validate1.cli";
							configd:validate "/opt/vyatta/share/tmplscripts/security/firewall/name/rule/destination/mac-address/configd_validate2.cli";
						}
						leaf address {
							type string {
								configd:syntax "/opt/vyatta/share/tmplscripts/security/firewall/name/rule/destination/address/configd_syntax1.cli";
								configd:syntax "/opt/vyatta/share/tmplscripts/security/firewall/name/rule/destination/address/configd_syntax2.cli";
							}
							configd:help "Destination IP address, subnet, or address-group";
							configd:validate "/opt/vyatta/share/tmplscripts/security/firewall/name/rule/destination/address/configd_validate1.cli";
							configd:validate "/opt/vyatta/share/tmplscripts/security/firewall/name/rule/destination/address/configd_validate2.cli";
							configd:validate "/opt/vyatta/share/tmplscripts/security/firewall/name/rule/destination/address/configd_validate3.cli";
							configd:validate "/opt/vyatta/share/tmplscripts/security/firewall/name/rule/destination/address/configd_validate4.cli";
							configd:validate "/opt/vyatta/share/tmplscripts/security/firewall/name/rule/destination/address/configd_validate5.cli";
						}
						leaf port {
							type string;
							configd:help "Destination port or port-group";
							configd:allowed "/opt/vyatta/share/tmplscripts/security/firewall/name/rule/destination/port/configd_allowed.sh";
							configd:validate "/opt/vyatta/share/tmplscripts/security/firewall/name/rule/destination/port/configd_validate1.cli";
							configd:validate "/opt/vyatta/share/tmplscripts/security/firewall/name/rule/destination/port/configd_validate2.cli";
						}
					}
					leaf dscp {
						type uint8 {
							range 0..63;
						}
						configd:help "DSCP value to match in an incoming IP header";
					}
					leaf state {
						type enumeration {
							enum "enable";
							enum "disable";
						}
						configd:help "Enable or disable state firewall rule";
					}
					leaf protocol {
						type string {
							configd:syntax "/opt/vyatta/share/tmplscripts/security/firewall/name/rule/protocol/configd_syntax1.cli";
							configd:syntax "/opt/vyatta/share/tmplscripts/security/firewall/name/rule/protocol/configd_syntax2.cli";
						}
						configd:help "Protocol to match (name or number)";
						configd:allowed "/opt/vyatta/share/tmplscripts/security/firewall/name/rule/protocol/configd_allowed.sh";
					}
					leaf ethertype {
						type string {
							configd:syntax "/opt/vyatta/share/tmplscripts/security/firewall/name/rule/ethertype/configd_syntax.cli";
						}
						configd:help "Ethertype to match (name or hex or decimal)";
						configd:allowed "/opt/vyatta/share/tmplscripts/security/firewall/name/rule/ethertype/configd_allowed.sh";
					}
				}
				leaf default-action {
					type enumeration {
						enum "drop" {
							configd:help "Drop if no prior rules are hit";
						}
						enum "accept" {
							configd:help "Accept if no prior rules are hit";
						}
					}
					configd:help "Default-action for rule-set";
					configd:end "/opt/vyatta/share/tmplscripts/security/firewall/name/default-action/configd_end.sh";
				}
				leaf default-log {
					type empty;
					configd:help "Default-log for rule-set";
					configd:end "/opt/vyatta/share/tmplscripts/security/firewall/name/default-log/configd_end.sh";
				}
			}
			container session-log {
				presence "true";
				configd:help "Session logging";
				container tcp {
					presence "true";
					configd:help "TCP";
					leaf close-wait {
						type empty;
						configd:help "close-wait state";
						configd:end "/opt/vyatta/share/tmplscripts/security/firewall/session-log/tcp/close-wait/configd_end.sh";
					}
					leaf established {
						type empty;
						configd:help "established state";
						configd:end "/opt/vyatta/share/tmplscripts/security/firewall/session-log/tcp/established/configd_end.sh";
					}
					leaf syn-sent {
						type empty;
						configd:help "syn-sent state";
						configd:end "/opt/vyatta/share/tmplscripts/security/firewall/session-log/tcp/syn-sent/configd_end.sh";
					}
					leaf fin-received {
						type empty;
						configd:help "fin-received state";
						configd:end "/opt/vyatta/share/tmplscripts/security/firewall/session-log/tcp/fin-received/configd_end.sh";
					}
					leaf fin-sent {
						type empty;
						configd:help "fin-sent state";
						configd:end "/opt/vyatta/share/tmplscripts/security/firewall/session-log/tcp/fin-sent/configd_end.sh";
					}
					leaf closing {
						type empty;
						configd:help "closing state";
						configd:end "/opt/vyatta/share/tmplscripts/security/firewall/session-log/tcp/closing/configd_end.sh";
					}
					leaf simsyn-sent {
						type empty;
						configd:help "simsyn-sent state";
						configd:end "/opt/vyatta/share/tmplscripts/security/firewall/session-log/tcp/simsyn-sent/configd_end.sh";
					}
					leaf time-wait {
						type empty;
						configd:help "time-wait state";
						configd:end "/opt/vyatta/share/tmplscripts/security/firewall/session-log/tcp/time-wait/configd_end.sh";
					}
					leaf last-ack {
						type empty;
						configd:help "last-ack state";
						configd:end "/opt/vyatta/share/tmplscripts/security/firewall/session-log/tcp/last-ack/configd_end.sh";
					}
					leaf syn-received {
						type empty;
						configd:help "syn-received state";
						configd:end "/opt/vyatta/share/tmplscripts/security/firewall/session-log/tcp/syn-received/configd_end.sh";
					}
					leaf fin-wait {
						type empty;
						configd:help "fin-wait state";
						configd:end "/opt/vyatta/share/tmplscripts/security/firewall/session-log/tcp/fin-wait/configd_end.sh";
					}
					leaf timeout {
						type empty;
						configd:help "time-out state";
						configd:end "/opt/vyatta/share/tmplscripts/security/firewall/session-log/tcp/timeout/configd_end.sh";
					}
				}
				container icmp {
					presence "true";
					configd:help "ICMP";
					leaf established {
						type empty;
						configd:help "established state";
						configd:end "/opt/vyatta/share/tmplscripts/security/firewall/session-log/icmp/established/configd_end.sh";
					}
					leaf closed {
						type empty;
						configd:help "closed state";
						configd:end "/opt/vyatta/share/tmplscripts/security/firewall/session-log/icmp/closed/configd_end.sh";
					}
					leaf timeout {
						type empty;
						configd:help "timeout state";
						configd:end "/opt/vyatta/share/tmplscripts/security/firewall/session-log/icmp/timeout/configd_end.sh";
					}
					leaf new {
						type empty;
						configd:help "new state";
						configd:end "/opt/vyatta/share/tmplscripts/security/firewall/session-log/icmp/new/configd_end.sh";
					}
				}
				container other {
					presence "true";
					configd:help "protocols other than TCP, UDP or ICMP";
					leaf established {
						type empty;
						configd:help "established state";
						configd:end "/opt/vyatta/share/tmplscripts/security/firewall/session-log/other/established/configd_end.sh";
					}
					leaf closed {
						type empty;
						configd:help "closed state";
						configd:end "/opt/vyatta/share/tmplscripts/security/firewall/session-log/other/closed/configd_end.sh";
					}
					leaf timeout {
						type empty;
						configd:help "timeout state";
						configd:end "/opt/vyatta/share/tmplscripts/security/firewall/session-log/other/timeout/configd_end.sh";
					}
					leaf new {
						type empty;
						configd:help "new state";
						configd:end "/opt/vyatta/share/tmplscripts/security/firewall/session-log/other/new/configd_end.sh";
					}
				}
				container udp {
					presence "true";
					configd:help "UDP";
					leaf established {
						type empty;
						configd:help "established state";
						configd:end "/opt/vyatta/share/tmplscripts/security/firewall/session-log/udp/established/configd_end.sh";
					}
					leaf closed {
						type empty;
						configd:help "closed state";
						configd:end "/opt/vyatta/share/tmplscripts/security/firewall/session-log/udp/closed/configd_end.sh";
					}
					leaf timeout {
						type empty;
						configd:help "timeout state";
						configd:end "/opt/vyatta/share/tmplscripts/security/firewall/session-log/udp/timeout/configd_end.sh";
					}
					leaf new {
						type empty;
						configd:help "new state";
						configd:end "/opt/vyatta/share/tmplscripts/security/firewall/session-log/udp/new/configd_end.sh";
					}
				}
			}
			container global-state-policy {
				presence "true";
				configd:help "Configure global state parameters for firewall";
				configd:end "/opt/vyatta/share/tmplscripts/security/firewall/global-state-policy/configd_end.sh";
				configd:validate "/opt/vyatta/share/tmplscripts/security/firewall/global-state-policy/configd_validate1.cli";
				leaf tcp {
					type empty;
					configd:help "enable tcp state monitoring for firewall";
				}
				leaf icmp {
					type empty;
					configd:help "enable icmp state monitoring for firewall";
				}
				leaf udp {
					type empty;
					configd:help "enable udp state monitoring for firewall";
				}
			}
			leaf config-trap {
				type enumeration {
					enum "enable" {
						configd:help "Enable sending SNMP trap on firewall configuration change";
					}
					enum "disable" {
						configd:help "Disable sending SNMP trap on firewall configuration change";
					}
				}
				configd:help "SNMP trap generation on firewall configuration changes";
				default "disable";
			}
		}
		container zone-policy {
			presence "true";
			configd:priority "350";
			configd:help "Zone-policy";
			configd:end "/opt/vyatta/share/tmplscripts/security/zone-policy/configd_end.sh";
			list zone {
				configd:help "Zone name";
				configd:end "/opt/vyatta/share/tmplscripts/security/zone-policy/zone/configd_end.sh";
				configd:validate "/opt/vyatta/share/tmplscripts/security/zone-policy/zone/configd_validate1.cli";
				configd:validate "/opt/vyatta/share/tmplscripts/security/zone-policy/zone/configd_validate2.cli";
				configd:validate "/opt/vyatta/share/tmplscripts/security/zone-policy/zone/configd_validate3.cli";
				key "tagnode";
				leaf tagnode {
					type string {
						pattern "[0-9A-Za-z][-_0-9A-Za-z]*" {
							error-message "only alpha-numeric policy name allowed";
						}
					}
					configd:help "Zone name";
				}
				leaf description {
					type string;
					configd:help "Zone description";
				}
				leaf-list interface {
					type string {
						configd:syntax "/opt/vyatta/share/tmplscripts/security/zone-policy/zone/interface/configd_syntax1.cli";
					}
					ordered-by "user";
					configd:help "Interface associated with zone";
					configd:allowed "/opt/vyatta/share/tmplscripts/security/zone-policy/zone/interface/configd_allowed.sh";
					configd:validate "/opt/vyatta/share/tmplscripts/security/zone-policy/zone/interface/configd_validate0.sh";
				}
				leaf default-action {
					type enumeration {
						enum "accept";
						enum "drop";
					}
					configd:help "Default-action for traffic leaving this zone";
					default "drop";
				}
				list to {
					configd:help "Output zone to filter traffic";
					configd:allowed "/opt/vyatta/share/tmplscripts/security/zone-policy/zone/to/configd_allowed.sh";
					configd:validate "/opt/vyatta/share/tmplscripts/security/zone-policy/zone/to/configd_validate1.cli";
					configd:validate "/opt/vyatta/share/tmplscripts/security/zone-policy/zone/to/configd_validate2.cli";
					key "tagnode";
					leaf tagnode {
						type string {
							pattern "[0-9A-Za-z][-_0-9A-Za-z]*" {
								error-message "only alpha-numeric policy name allowed";
							}
						}
						configd:help "Output zone to filter traffic";
						configd:allowed "/opt/vyatta/share/tmplscripts/security/zone-policy/zone/to/configd_allowed.sh";
					}
					leaf-list firewall {
						type string {
							pattern "[0-9A-Za-z][-_0-9A-Za-z]*" {
								error-message "only alpha-numeric policy name allowed";
							}
						}
						ordered-by "user";
						configd:help "Ruleset for forwarded packets on inbound interface";
						configd:allowed "/opt/vyatta/share/tmplscripts/security/zone-policy/zone/to/firewall/configd_allowed.sh";
						configd:validate "/opt/vyatta/share/tmplscripts/security/zone-policy/zone/to/firewall/configd_validate1.cli";
					}
				}
			}
		}
	}
	augment /if:interfaces/interfaces-bridge:bridge {
		container firewall {
			presence "true";
			configd:help "Firewall options";
			configd:end "/opt/vyatta/share/tmplscripts/interfaces/bridge/firewall/configd_end.sh";
			configd:validate "/opt/vyatta/share/tmplscripts/interfaces/bridge/firewall/configd_validate1.cli";
			configd:validate "/opt/vyatta/share/tmplscripts/interfaces/bridge/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/bridge/firewall/out/configd_allowed.sh";
				configd:validate "/opt/vyatta/share/tmplscripts/interfaces/bridge/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/bridge/firewall/in/configd_allowed.sh";
				configd:validate "/opt/vyatta/share/tmplscripts/interfaces/bridge/firewall/in/configd_validate1.cli";
			}
			leaf-list l2 {
				type string {
					pattern "[0-9A-Za-z][-_0-9A-Za-z]*" {
						error-message "only alpha-numeric policy name allowed";
					}
				}
				ordered-by "user";
				configd:help "Ruleset for forwarded packets on bridge interface";
				configd:allowed "/opt/vyatta/share/tmplscripts/interfaces/bridge/firewall/l2/configd_allowed.sh";
				configd:validate "/opt/vyatta/share/tmplscripts/interfaces/bridge/firewall/l2/configd_validate1.cli";
			}
		}
	}
	augment /if:interfaces/interfaces-dataplane:dataplane {
		container firewall {
			presence "true";
			configd:help "Firewall options";
			configd:end "/opt/vyatta/share/tmplscripts/interfaces/dataplane/firewall/configd_end.sh";
			configd:validate "/opt/vyatta/share/tmplscripts/interfaces/dataplane/firewall/configd_validate1.cli";
			configd:validate "/opt/vyatta/share/tmplscripts/interfaces/dataplane/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/dataplane/firewall/out/configd_allowed.sh";
				configd:validate "/opt/vyatta/share/tmplscripts/interfaces/dataplane/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/dataplane/firewall/in/configd_allowed.sh";
				configd:validate "/opt/vyatta/share/tmplscripts/interfaces/dataplane/firewall/in/configd_validate1.cli";
			}
		}
	}
	augment /if:interfaces/interfaces-dataplane:dataplane/interfaces-dataplane:vif {
		container firewall {
			presence "true";
			configd:help "Firewall options";
			configd:end "/opt/vyatta/share/tmplscripts/interfaces/dataplane/vif/firewall/configd_end.sh";
			configd:validate "/opt/vyatta/share/tmplscripts/interfaces/dataplane/vif/firewall/configd_validate1.cli";
			configd:validate "/opt/vyatta/share/tmplscripts/interfaces/dataplane/vif/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/dataplane/vif/firewall/out/configd_allowed.sh";
				configd:validate "/opt/vyatta/share/tmplscripts/interfaces/dataplane/vif/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/dataplane/vif/firewall/in/configd_allowed.sh";
				configd:validate "/opt/vyatta/share/tmplscripts/interfaces/dataplane/vif/firewall/in/configd_validate1.cli";
			}
		}
	}
	augment /if:interfaces/interfaces-l2tpeth:l2tpeth {
		container firewall {
			presence "true";
			configd:help "Firewall options";
			configd:end "/opt/vyatta/share/tmplscripts/interfaces/l2tpeth/firewall/configd_end.sh";
			configd:validate "/opt/vyatta/share/tmplscripts/interfaces/l2tpeth/firewall/configd_validate1.cli";
			configd:validate "/opt/vyatta/share/tmplscripts/interfaces/l2tpeth/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/l2tpeth/firewall/out/configd_allowed.sh";
				configd:validate "/opt/vyatta/share/tmplscripts/interfaces/l2tpeth/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/l2tpeth/firewall/in/configd_allowed.sh";
				configd:validate "/opt/vyatta/share/tmplscripts/interfaces/l2tpeth/firewall/in/configd_validate1.cli";
			}
		}
	}
	augment /if:interfaces/interfaces-l2tpeth:l2tpeth/interfaces-l2tpeth:vif {
		container firewall {
			presence "true";
			configd:help "Firewall options";
			configd:end "/opt/vyatta/share/tmplscripts/interfaces/l2tpeth/vif/firewall/configd_end.sh";
			configd:validate "/opt/vyatta/share/tmplscripts/interfaces/l2tpeth/vif/firewall/configd_validate1.cli";
			configd:validate "/opt/vyatta/share/tmplscripts/interfaces/l2tpeth/vif/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/l2tpeth/vif/firewall/out/configd_allowed.sh";
				configd:validate "/opt/vyatta/share/tmplscripts/interfaces/l2tpeth/vif/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/l2tpeth/vif/firewall/in/configd_allowed.sh";
				configd:validate "/opt/vyatta/share/tmplscripts/interfaces/l2tpeth/vif/firewall/in/configd_validate1.cli";
			}
		}
	}
	augment /if:interfaces/interfaces-openvpn:openvpn {
		container firewall {
			presence "true";
			configd:help "Firewall options";
			configd:end "/opt/vyatta/share/tmplscripts/interfaces/openvpn/firewall/configd_end.sh";
			configd:validate "/opt/vyatta/share/tmplscripts/interfaces/openvpn/firewall/configd_validate1.cli";
			configd:validate "/opt/vyatta/share/tmplscripts/interfaces/openvpn/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/openvpn/firewall/out/configd_allowed.sh";
				configd:validate "/opt/vyatta/share/tmplscripts/interfaces/openvpn/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/openvpn/firewall/in/configd_allowed.sh";
				configd:validate "/opt/vyatta/share/tmplscripts/interfaces/openvpn/firewall/in/configd_validate1.cli";
			}
		}
	}
	augment /if:interfaces/interfaces-tunnel:tunnel {
		container firewall {
			presence "true";
			configd:help "Firewall options";
			configd:end "/opt/vyatta/share/tmplscripts/interfaces/tunnel/firewall/configd_end.sh";
			configd:validate "/opt/vyatta/share/tmplscripts/interfaces/tunnel/firewall/configd_validate1.cli";
			configd:validate "/opt/vyatta/share/tmplscripts/interfaces/tunnel/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/tunnel/firewall/out/configd_allowed.sh";
				configd:validate "/opt/vyatta/share/tmplscripts/interfaces/tunnel/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/tunnel/firewall/in/configd_allowed.sh";
				configd:validate "/opt/vyatta/share/tmplscripts/interfaces/tunnel/firewall/in/configd_validate1.cli";
			}
		}
	}
	augment /if:interfaces/interfaces-vti:vti {
		container firewall {
			presence "true";
			configd:help "Firewall options";
			configd:end "/opt/vyatta/share/tmplscripts/interfaces/vti/firewall/configd_end.sh";
			configd:validate "/opt/vyatta/share/tmplscripts/interfaces/vti/firewall/configd_validate1.cli";
			configd:validate "/opt/vyatta/share/tmplscripts/interfaces/vti/firewall/configd_validate2.cli";
			leaf-list out {
				type string {
					pattern "[0-9A-Za-z][-_0-9A-Za-z]*" {
						error-message "only alpha-numeric policy name allowed";
					}
				}
				ordered-by "user";
				configd:help "Ruleset for forwarded packets on outbound interface";
				configd:allowed "/opt/vyatta/share/tmplscripts/interfaces/vti/firewall/out/configd_allowed.sh";
				configd:validate "/opt/vyatta/share/tmplscripts/interfaces/vti/firewall/out/configd_validate1.cli";
			}
			leaf-list in {
				type string {
					pattern "[0-9A-Za-z][-_0-9A-Za-z]*" {
						error-message "only alpha-numeric policy name allowed";
					}
				}
				ordered-by "user";
				configd:help "Ruleset for forwarded packets on inbound interface";
				configd:allowed "/opt/vyatta/share/tmplscripts/interfaces/vti/firewall/in/configd_allowed.sh";
				configd:validate "/opt/vyatta/share/tmplscripts/interfaces/vti/firewall/in/configd_validate1.cli";
			}
		}
	}
}
