module vyatta-system-fips {
	namespace "urn:vyatta.com:mgmt:vyatta-system-fips";
	prefix system-fips;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /system:system {
		container fips {
			presence "true";
			configd:help "Enable FIPS mode - this operation is irreversible";
			leaf enable {
				type empty;
				configd:help "Enable FIPS mode - this operation is irreversible";
				configd:create "vyatta-grub-enable-fips";
			}
			configd:validate "/opt/vyatta/share/tmplscripts/system/fips/configd_validate1.cli";
		}
	}
}
