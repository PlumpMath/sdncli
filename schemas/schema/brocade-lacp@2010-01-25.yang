/***********************************************************************
 * brocade-lacp.yang: Brocade LACP data model
 *
 * January 2010, Mobin Mohan
 *
 * Copyright (c) 2010 by Brocade Communications Systems, Inc.
 * All rights reserved.
 *
 **********************************************************************/

module brocade-lacp {
    namespace "urn:brocade.com:mgmt:brocade-lacp";
    prefix "lacp";
	
    import tailf-common { prefix tailf;	}

    import brocade-interface {
        prefix interface;
    }

    /* Meta Information */
    organization 
        "Brocade Communications Systems, Inc.";
    
    contact
        "Brocade Communications Systems, Inc.
         Postal: 1745 Technology Drive,
                 San Jose, CA 95110 
                  U.S.A
         Tel: +1-408-392-6061
         E-mail: support@Brocade.com 
         web: www.brocade.com.";
    
    description 
        "This module describes the data model for Link Aggregation 
         Control Protocol";

   	/* Revision history */
   	revision "2010-01-25" {
       	description "Initial Version";
   	}

 
	/* lacp configurations */
	container lacp {

		leaf system-priority {
			type uint32 {
				range "1 .. 65535" {
				}
			}
    		default 32768;
		}
	}
    grouping common-phy-lacp-cmds {
		container lacp {
    
    		leaf timeout {
				type enumeration {
					enum short {
						value 1;
					}
					enum long {
						value 2;
					}
				}
			}
			leaf std_port-priority {
	 	 		description "This command is used to configure port priority";

	  			type uint32 {
			  		range "1 .. 65535" {
			  	}
	  		}
	  			default 32768;
			}
			
			leaf default-up {
			    type empty;
			}
			

		}
    }

	augment "/interface:interface/interface:tengigabitethernet" {
        uses common-phy-lacp-cmds;
	}
	augment "/interface:interface/interface:gigabitethernet" {
        uses common-phy-lacp-cmds;
	}
	augment "/interface:interface/interface:fortygigabitethernet" {
        uses common-phy-lacp-cmds;
	}
    augment "/interface:interface/interface:hundredgigabitethernet" {
        uses common-phy-lacp-cmds;
    }

}
