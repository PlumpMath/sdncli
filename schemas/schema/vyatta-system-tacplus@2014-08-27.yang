module vyatta-system-tacplus {
	namespace "urn:vyatta.com:mgmt:vyatta-system-tacplus";
	prefix system-tacplus;

	import vyatta-system {
		prefix system;
	}
	import vyatta-system-login {
		prefix system-login;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /system:system {
		container tacplus-options {
			presence "true";
			configd:help "TACACS+ accounting";
			leaf command-accounting {
				type empty;
				configd:priority "410";
				configd:help "TACACS+ command accounting";
				configd:create "/opt/vyatta/share/tmplscripts/system/tacplus-options/command-accounting/configd_create.sh";
				configd:delete "/opt/vyatta/share/tmplscripts/system/tacplus-options/command-accounting/configd_delete.sh";
			}
		}
	}
	augment /system:system/system-login:login {
		list tacplus-server {
			configd:help "TACACS+ server address";
			configd:validate "/opt/vyatta/share/tmplscripts/system/login/tacplus-server/configd_validate1.cli";
			key "tagnode";
			leaf tagnode {
				type union {
					type types:ipv4-address;
					type types:ipv6-address;
				}
				configd:help "TACACS+ server address";
			}
			leaf source-address {
				type union {
					type types:ipv4-address;
					type types:ipv6-address;
				}
				configd:help "Source address to use for connecting to TACACS+ server";
			}
			leaf port {
				type uint32 {
					range 1..65535 {
						error-message "port must be between 1 and 65535";
					}
				}
				configd:help "TACACS+ server port";
				default "49";
			}
			leaf secret {
				type string {
					pattern "[!-~]+" {
						error-message "Secret must not contain space";
					}
				}
				configd:help "Secret for TACACS+ access [REQUIRED]";
				configd:secret "true";
			}
			leaf timeout {
				type uint32 {
					range 1..30 {
						error-message "Timeout must be between 1 and 30 seconds";
					}
				}
				configd:help "Timeout for TACACS+ session";
				default "3";
			}
		}
	}
}
