module vyatta-protocols-pim6 {
	namespace "urn:vyatta.com:mgmt:vyatta-protocols-pim6";
	prefix protocols-pim6;

	import vyatta-types {
		prefix types;
	}
	import vyatta-protocols {
		prefix protocols;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}
	import vyatta-interfaces-vti {
		prefix interfaces-vti;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /protocols:protocols {
		container pim6 {
			presence "true";
			configd:priority "750";
			configd:help "IPv6 Protocol Independent Multicasting (PIM)";
			configd:validate "/opt/vyatta/share/tmplscripts/protocols/pim6/configd_validate1.cli";
			container register-source {
				presence "true";
				configd:help "Configure the source address of Register packets sent by this DR";
				configd:delete "/opt/vyatta/share/tmplscripts/protocols/pim6/register-source/configd_delete.sh";
				configd:end "/opt/vyatta/share/tmplscripts/protocols/pim6/register-source/configd_end.sh";
				configd:validate "/opt/vyatta/share/tmplscripts/protocols/pim6/register-source/configd_validate1.cli";
				configd:validate "/opt/vyatta/share/tmplscripts/protocols/pim6/register-source/configd_validate2.cli";
				leaf interface {
					type string;
					configd:help "The name of the interface to use as the source of the register packets";
					configd:allowed "/opt/vyatta/share/tmplscripts/protocols/pim6/register-source/interface/configd_allowed.sh";
					configd:validate "/opt/vyatta/share/tmplscripts/protocols/pim6/register-source/interface/configd_validate1.cli";
				}
				leaf address {
					type types:ipv6-address;
					configd:help "IPv6 address to use as the source of the register packets";
				}
			}
			container bsr-candidate {
				presence "true";
				configd:help "BSR-candidate configuration";
				configd:delete "/opt/vyatta/share/tmplscripts/protocols/pim6/bsr-candidate/configd_delete.sh";
				configd:end "/opt/vyatta/share/tmplscripts/protocols/pim6/bsr-candidate/configd_end.sh";
				configd:validate "/opt/vyatta/share/tmplscripts/protocols/pim6/bsr-candidate/configd_validate1.cli";
				configd:validate "/opt/vyatta/share/tmplscripts/protocols/pim6/bsr-candidate/configd_validate2.cli";
				leaf priority {
					type uint32 {
						range 0..255 {
							error-message "Must be between 0-255";
						}
					}
					configd:help "Priority for a BSR candidate";
				}
				leaf interface {
					type string;
					configd:help "BSR-candidate interface name";
					configd:allowed "/opt/vyatta/share/tmplscripts/protocols/pim6/bsr-candidate/interface/configd_allowed.sh";
					configd:validate "/opt/vyatta/share/tmplscripts/protocols/pim6/bsr-candidate/interface/configd_validate0.sh";
				}
				leaf hash-mask {
					type uint32 {
						range 0..128 {
							error-message "Must be between 0-128";
						}
					}
					configd:help "Hash mask length for RP selection";
				}
			}
			leaf rp-embedded {
				type empty;
				configd:help "Turn on IPv6 RP Embedded";
				configd:create "/opt/vyatta/share/tmplscripts/protocols/pim6/rp-embedded/configd_create.sh";
				configd:delete "/opt/vyatta/share/tmplscripts/protocols/pim6/rp-embedded/configd_delete.sh";
			}
			leaf ignore-rp-set-priority {
				type empty;
				configd:help "Ignore the RP-SET priority value, and use only the hashing mechanism for RP selection";
				configd:create "/opt/vyatta/share/tmplscripts/protocols/pim6/ignore-rp-set-priority/configd_create.sh";
				configd:delete "/opt/vyatta/share/tmplscripts/protocols/pim6/ignore-rp-set-priority/configd_delete.sh";
			}
			list anycast-rp {
				configd:help "Configure the Anycast RP in the RP set";
				configd:delete "/opt/vyatta/share/tmplscripts/protocols/pim6/anycast-rp/configd_delete.sh";
				configd:validate "/opt/vyatta/share/tmplscripts/protocols/pim6/anycast-rp/configd_validate1.cli";
				key "tagnode";
				leaf tagnode {
					type types:ipv6-address;
					configd:help "Configure the Anycast RP in the RP set";
				}
				leaf-list anycast-rp-peer {
					type types:ipv6-address;
					ordered-by "user";
					configd:help "Destination IPv6 address where Register messages are copied and sent";
					configd:create "/opt/vyatta/share/tmplscripts/protocols/pim6/anycast-rp/anycast-rp-peer/configd_create.sh";
					configd:delete "/opt/vyatta/share/tmplscripts/protocols/pim6/anycast-rp/anycast-rp-peer/configd_delete.sh";
				}
			}
			leaf register-rp-reachability {
				type empty;
				configd:help "Enable the RP reachability check for IPv6 PIM Registers at the DR";
				configd:create "/opt/vyatta/share/tmplscripts/protocols/pim6/register-rp-reachability/configd_create.sh";
				configd:delete "/opt/vyatta/share/tmplscripts/protocols/pim6/register-rp-reachability/configd_delete.sh";
			}
			container accept-register {
				presence "true";
				configd:help "Configure the ability to filter out multicast sources specified by the given access-list at the RP";
				configd:validate "/opt/vyatta/share/tmplscripts/protocols/pim6/accept-register/configd_validate1.cli";
				leaf list {
					type string {
						configd:syntax "/opt/vyatta/share/tmplscripts/protocols/pim6/accept-register/list/configd_syntax1.cli";
					}
					configd:help "Specify access list";
					configd:allowed "/opt/vyatta/share/tmplscripts/protocols/pim6/accept-register/list/configd_allowed.sh";
					configd:update "/opt/vyatta/share/tmplscripts/protocols/pim6/accept-register/list/configd_update.sh";
					configd:delete "/opt/vyatta/share/tmplscripts/protocols/pim6/accept-register/list/configd_delete.sh";
					configd:validate "/opt/vyatta/share/tmplscripts/protocols/pim6/accept-register/list/configd_validate1.cli";
				}
			}
			list spt-threshold {
				configd:help "Turn off the ability of the last-hop PIM router to switch to SPT";
				configd:allowed "/opt/vyatta/share/tmplscripts/protocols/pim6/spt-threshold/configd_allowed.sh";
				configd:delete "/opt/vyatta/share/tmplscripts/protocols/pim6/spt-threshold/configd_delete.sh";
				configd:end "/opt/vyatta/share/tmplscripts/protocols/pim6/spt-threshold/configd_end.sh";
				key "tagnode";
				leaf tagnode {
					type string {
						configd:syntax "/opt/vyatta/share/tmplscripts/protocols/pim6/spt-threshold/configd_syntax1.cli";
					}
					configd:help "Turn off the ability of the last-hop PIM router to switch to SPT";
					configd:allowed "/opt/vyatta/share/tmplscripts/protocols/pim6/spt-threshold/configd_allowed.sh";
				}
				leaf group-list {
					type string {
						configd:syntax "/opt/vyatta/share/tmplscripts/protocols/pim6/spt-threshold/group-list/configd_syntax1.cli";
					}
					configd:help "Enable the ability for the last-hop PIM router to switch to SPT for multicast group addresses indicated by the given access-list";
					configd:allowed "/opt/vyatta/share/tmplscripts/protocols/pim6/spt-threshold/group-list/configd_allowed.sh";
					configd:delete "/opt/vyatta/share/tmplscripts/protocols/pim6/spt-threshold/group-list/configd_delete.sh";
					configd:end "/opt/vyatta/share/tmplscripts/protocols/pim6/spt-threshold/group-list/configd_end.sh";
					configd:validate "/opt/vyatta/share/tmplscripts/protocols/pim6/spt-threshold/group-list/configd_validate1.cli";
				}
			}
			container legacy-register-checksum {
				presence "true";
				configd:help "Configure the option to calculate the register checksum over the whole packet";
				configd:delete "/opt/vyatta/share/tmplscripts/protocols/pim6/legacy-register-checksum/configd_delete.sh";
				configd:end "/opt/vyatta/share/tmplscripts/protocols/pim6/legacy-register-checksum/configd_end.sh";
				leaf group-list {
					type string {
						configd:syntax "/opt/vyatta/share/tmplscripts/protocols/pim6/legacy-register-checksum/group-list/configd_syntax1.cli";
					}
					configd:help "Configure the option to calculate the register checksum over the whole packet on multicast groups specified by the access-list";
					configd:allowed "/opt/vyatta/share/tmplscripts/protocols/pim6/legacy-register-checksum/group-list/configd_allowed.sh";
					configd:validate "/opt/vyatta/share/tmplscripts/protocols/pim6/legacy-register-checksum/group-list/configd_validate1.cli";
				}
			}
			leaf register-kat {
				type uint32 {
					range 1..65535 {
						error-message "Must be between 1-65535";
					}
				}
				configd:help "Configure a Keepalive Timer (KAT) value for (S,G) states at RP to monitor IPv6 PIM register packets";
				configd:update "/opt/vyatta/share/tmplscripts/protocols/pim6/register-kat/configd_update.sh";
				configd:delete "/opt/vyatta/share/tmplscripts/protocols/pim6/register-kat/configd_delete.sh";
			}
			container rp-candidate {
				presence "true";
				configd:help "rp-candidate configuration";
				configd:validate "/opt/vyatta/share/tmplscripts/protocols/pim6/rp-candidate/configd_validate1.cli";
				list interface {
					configd:help "RP-candidate interface name";
					configd:allowed "/opt/vyatta/share/tmplscripts/protocols/pim6/rp-candidate/interface/configd_allowed.sh";
					configd:validate "/opt/vyatta/share/tmplscripts/protocols/pim6/rp-candidate/interface/configd_validate0.sh";
					configd:delete "/opt/vyatta/share/tmplscripts/protocols/pim6/rp-candidate/interface/configd_delete.sh";
					configd:end "/opt/vyatta/share/tmplscripts/protocols/pim6/rp-candidate/interface/configd_end.sh";
					key "tagnode";
					leaf tagnode {
						type string;
						configd:help "RP-candidate interface name";
						configd:allowed "/opt/vyatta/share/tmplscripts/protocols/pim6/rp-candidate/interface/configd_allowed.sh";
					}
					leaf priority {
						type uint32 {
							range 0..255 {
								error-message "Must be between 0-255";
							}
						}
						configd:help "A candidate-RP priority";
					}
					leaf interval {
						type uint32 {
							range 0..16383 {
								error-message "Must be between 0-16383";
							}
						}
						configd:help "A candidate-RP advertisement interval";
					}
					leaf group-list {
						type string {
							configd:syntax "/opt/vyatta/share/tmplscripts/protocols/pim6/rp-candidate/interface/group-list/configd_syntax1.cli";
						}
						configd:help "Specify the group ranges for this candidate RP";
						configd:allowed "/opt/vyatta/share/tmplscripts/protocols/pim6/rp-candidate/interface/group-list/configd_allowed.sh";
						configd:validate "/opt/vyatta/share/tmplscripts/protocols/pim6/rp-candidate/interface/group-list/configd_validate1.cli";
					}
				}
			}
			leaf register-suppression-timer {
				type uint32 {
					range 11..65535 {
						error-message "Must be between 11-65535";
					}
				}
				configd:help "Configure the register-suppression time";
				configd:update "/opt/vyatta/share/tmplscripts/protocols/pim6/register-suppression-timer/configd_update.sh";
				configd:delete "/opt/vyatta/share/tmplscripts/protocols/pim6/register-suppression-timer/configd_delete.sh";
			}
			leaf join-prune-timer {
				type uint32 {
					range 1..65535 {
						error-message "Must be between 1-65535";
					}
				}
				configd:help "Set a IPv6 PIM join/prune timer";
				configd:update "/opt/vyatta/share/tmplscripts/protocols/pim6/join-prune-timer/configd_update.sh";
				configd:delete "/opt/vyatta/share/tmplscripts/protocols/pim6/join-prune-timer/configd_delete.sh";
			}
			leaf register-rate-limit {
				type uint32 {
					range 1..65535 {
						error-message "Must be between 1-65535";
					}
				}
				configd:help "Configure the rate of Register packets sent by this designated router (DR)";
				configd:update "/opt/vyatta/share/tmplscripts/protocols/pim6/register-rate-limit/configd_update.sh";
				configd:delete "/opt/vyatta/share/tmplscripts/protocols/pim6/register-rate-limit/configd_delete.sh";
			}
			container ssm {
				presence "true";
				configd:help "Configure Source Specific Multicast (SSM)";
				configd:delete "/opt/vyatta/share/tmplscripts/protocols/pim6/ssm/configd_delete.sh";
				configd:end "/opt/vyatta/share/tmplscripts/protocols/pim6/ssm/configd_end.sh";
				configd:validate "/opt/vyatta/share/tmplscripts/protocols/pim6/ssm/configd_validate1.cli";
				configd:validate "/opt/vyatta/share/tmplscripts/protocols/pim6/ssm/configd_validate2.cli";
				leaf default {
					type empty;
					configd:help "Defines the FF3x::/32 group range for SSM";
				}
				leaf range {
					type string {
						configd:syntax "/opt/vyatta/share/tmplscripts/protocols/pim6/ssm/range/configd_syntax1.cli";
					}
					configd:help "Define an access-list for group range to use for SSM";
					configd:allowed "/opt/vyatta/share/tmplscripts/protocols/pim6/ssm/range/configd_allowed.sh";
					configd:validate "/opt/vyatta/share/tmplscripts/protocols/pim6/ssm/range/configd_validate1.cli";
				}
			}
			list rp-address {
				configd:help "Statically configure an IPV6 RP address for multicast groups";
				configd:delete "/opt/vyatta/share/tmplscripts/protocols/pim6/rp-address/configd_delete.sh";
				configd:end "/opt/vyatta/share/tmplscripts/protocols/pim6/rp-address/configd_end.sh";
				key "tagnode";
				leaf tagnode {
					type types:ipv6-address;
					configd:help "Statically configure an IPV6 RP address for multicast groups";
				}
				leaf list {
					type string {
						configd:syntax "/opt/vyatta/share/tmplscripts/protocols/pim6/rp-address/list/configd_syntax1.cli";
					}
					configd:help "Configure IPv6 static-RP address for specific group ranges";
					configd:allowed "/opt/vyatta/share/tmplscripts/protocols/pim6/rp-address/list/configd_allowed.sh";
					configd:validate "/opt/vyatta/share/tmplscripts/protocols/pim6/rp-address/list/configd_validate1.cli";
				}
				leaf override {
					type empty;
					configd:help "Set to take precedence over dynamically learned mappings";
				}
			}
		}
	}
	augment /if:interfaces/interfaces-bridge:bridge/interfaces-bridge:ipv6 {
		container pim {
			presence "true";
			configd:help "Protocol Independent Multicasting (PIM)";
			configd:validate "/opt/vyatta/share/tmplscripts/interfaces/bridge/ipv6/pim/configd_validate1.cli";
			configd:validate "/opt/vyatta/share/tmplscripts/interfaces/bridge/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/bridge/ipv6/pim/propagation-delay/configd_allowed.sh";
				configd:update "/opt/vyatta/share/tmplscripts/interfaces/bridge/ipv6/pim/propagation-delay/configd_update.sh";
				configd:delete "/opt/vyatta/share/tmplscripts/interfaces/bridge/ipv6/pim/propagation-delay/configd_delete.sh";
			}
			leaf unicast-bsm {
				type empty;
				configd:help "Enable support for sending and receiving unicast Bootstrap Messages (BSM) on an interface";
				configd:create "/opt/vyatta/share/tmplscripts/interfaces/bridge/ipv6/pim/unicast-bsm/configd_create.sh";
				configd:delete "/opt/vyatta/share/tmplscripts/interfaces/bridge/ipv6/pim/unicast-bsm/configd_delete.sh";
			}
			leaf neighbor-filter {
				type string;
				configd:help "Enable filtering of neighbors on the interface";
				configd:allowed "/opt/vyatta/share/tmplscripts/interfaces/bridge/ipv6/pim/neighbor-filter/configd_allowed.sh";
				configd:update "/opt/vyatta/share/tmplscripts/interfaces/bridge/ipv6/pim/neighbor-filter/configd_update.sh";
				configd:delete "/opt/vyatta/share/tmplscripts/interfaces/bridge/ipv6/pim/neighbor-filter/configd_delete.sh";
				configd:validate "/opt/vyatta/share/tmplscripts/interfaces/bridge/ipv6/pim/neighbor-filter/configd_validate1.cli";
			}
			container state-refresh {
				presence "true";
				configd:help "PIM-DM State Refresh";
				configd:validate "/opt/vyatta/share/tmplscripts/interfaces/bridge/ipv6/pim/state-refresh/configd_validate1.cli";
				leaf origination-interval {
					type uint32 {
						range 1..100 {
							error-message "Must be between 1-100";
						}
					}
					configd:help "Configure an origination interval value";
					configd:update "/opt/vyatta/share/tmplscripts/interfaces/bridge/ipv6/pim/state-refresh/origination-interval/configd_update.sh";
					configd:delete "/opt/vyatta/share/tmplscripts/interfaces/bridge/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/bridge/ipv6/pim/hello-interval/configd_update.sh";
				configd:delete "/opt/vyatta/share/tmplscripts/interfaces/bridge/ipv6/pim/hello-interval/configd_delete.sh";
				configd:validate "/opt/vyatta/share/tmplscripts/interfaces/bridge/ipv6/pim/hello-interval/configd_validate1.cli";
			}
			leaf bsr-border {
				type empty;
				configd:help "Disable bootstrap router (BSR) messages from being sent or received through an interface";
				configd:create "/opt/vyatta/share/tmplscripts/interfaces/bridge/ipv6/pim/bsr-border/configd_create.sh";
				configd:delete "/opt/vyatta/share/tmplscripts/interfaces/bridge/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/bridge/ipv6/pim/mode/configd_allowed.sh";
				configd:update "/opt/vyatta/share/tmplscripts/interfaces/bridge/ipv6/pim/mode/configd_update.sh";
				configd:delete "/opt/vyatta/share/tmplscripts/interfaces/bridge/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/bridge/ipv6/pim/hello-holdtime/configd_update.sh";
				configd:delete "/opt/vyatta/share/tmplscripts/interfaces/bridge/ipv6/pim/hello-holdtime/configd_delete.sh";
				configd:validate "/opt/vyatta/share/tmplscripts/interfaces/bridge/ipv6/pim/hello-holdtime/configd_validate1.cli";
				configd:validate "/opt/vyatta/share/tmplscripts/interfaces/bridge/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/bridge/ipv6/pim/dr-priority/configd_update.sh";
				configd:delete "/opt/vyatta/share/tmplscripts/interfaces/bridge/ipv6/pim/dr-priority/configd_delete.sh";
			}
			leaf exclude-genid {
				type empty;
				configd:help "Exclude the GenID (generated ID) option from Hello packets on an interface";
				configd:create "/opt/vyatta/share/tmplscripts/interfaces/bridge/ipv6/pim/exclude-genid/configd_create.sh";
				configd:delete "/opt/vyatta/share/tmplscripts/interfaces/bridge/ipv6/pim/exclude-genid/configd_delete.sh";
			}
		}
	}
	augment /if:interfaces/interfaces-dataplane:dataplane/interfaces-dataplane:ipv6 {
		container pim {
			presence "true";
			configd:help "Protocol Independent Multicasting (PIM)";
			configd:validate "/opt/vyatta/share/tmplscripts/interfaces/dataplane/ipv6/pim/configd_validate1.cli";
			configd:validate "/opt/vyatta/share/tmplscripts/interfaces/dataplane/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/dataplane/ipv6/pim/propagation-delay/configd_allowed.sh";
				configd:update "/opt/vyatta/share/tmplscripts/interfaces/dataplane/ipv6/pim/propagation-delay/configd_update.sh";
				configd:delete "/opt/vyatta/share/tmplscripts/interfaces/dataplane/ipv6/pim/propagation-delay/configd_delete.sh";
			}
			leaf unicast-bsm {
				type empty;
				configd:help "Enable support for sending and receiving unicast Bootstrap Messages (BSM) on an interface";
				configd:create "/opt/vyatta/share/tmplscripts/interfaces/dataplane/ipv6/pim/unicast-bsm/configd_create.sh";
				configd:delete "/opt/vyatta/share/tmplscripts/interfaces/dataplane/ipv6/pim/unicast-bsm/configd_delete.sh";
			}
			leaf neighbor-filter {
				type string;
				configd:help "Enable filtering of neighbors on the interface";
				configd:allowed "/opt/vyatta/share/tmplscripts/interfaces/dataplane/ipv6/pim/neighbor-filter/configd_allowed.sh";
				configd:update "/opt/vyatta/share/tmplscripts/interfaces/dataplane/ipv6/pim/neighbor-filter/configd_update.sh";
				configd:delete "/opt/vyatta/share/tmplscripts/interfaces/dataplane/ipv6/pim/neighbor-filter/configd_delete.sh";
				configd:validate "/opt/vyatta/share/tmplscripts/interfaces/dataplane/ipv6/pim/neighbor-filter/configd_validate1.cli";
			}
			container state-refresh {
				presence "true";
				configd:help "PIM-DM State Refresh";
				configd:validate "/opt/vyatta/share/tmplscripts/interfaces/dataplane/ipv6/pim/state-refresh/configd_validate1.cli";
				leaf origination-interval {
					type uint32 {
						range 1..100 {
							error-message "Must be between 1-100";
						}
					}
					configd:help "Configure an origination interval value";
					configd:update "/opt/vyatta/share/tmplscripts/interfaces/dataplane/ipv6/pim/state-refresh/origination-interval/configd_update.sh";
					configd:delete "/opt/vyatta/share/tmplscripts/interfaces/dataplane/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/dataplane/ipv6/pim/hello-interval/configd_update.sh";
				configd:delete "/opt/vyatta/share/tmplscripts/interfaces/dataplane/ipv6/pim/hello-interval/configd_delete.sh";
				configd:validate "/opt/vyatta/share/tmplscripts/interfaces/dataplane/ipv6/pim/hello-interval/configd_validate1.cli";
			}
			leaf bsr-border {
				type empty;
				configd:help "Disable bootstrap router (BSR) messages from being sent or received through an interface";
				configd:create "/opt/vyatta/share/tmplscripts/interfaces/dataplane/ipv6/pim/bsr-border/configd_create.sh";
				configd:delete "/opt/vyatta/share/tmplscripts/interfaces/dataplane/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/dataplane/ipv6/pim/mode/configd_allowed.sh";
				configd:update "/opt/vyatta/share/tmplscripts/interfaces/dataplane/ipv6/pim/mode/configd_update.sh";
				configd:delete "/opt/vyatta/share/tmplscripts/interfaces/dataplane/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/dataplane/ipv6/pim/hello-holdtime/configd_update.sh";
				configd:delete "/opt/vyatta/share/tmplscripts/interfaces/dataplane/ipv6/pim/hello-holdtime/configd_delete.sh";
				configd:validate "/opt/vyatta/share/tmplscripts/interfaces/dataplane/ipv6/pim/hello-holdtime/configd_validate1.cli";
				configd:validate "/opt/vyatta/share/tmplscripts/interfaces/dataplane/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/dataplane/ipv6/pim/dr-priority/configd_update.sh";
				configd:delete "/opt/vyatta/share/tmplscripts/interfaces/dataplane/ipv6/pim/dr-priority/configd_delete.sh";
			}
			leaf exclude-genid {
				type empty;
				configd:help "Exclude the GenID (generated ID) option from Hello packets on an interface";
				configd:create "/opt/vyatta/share/tmplscripts/interfaces/dataplane/ipv6/pim/exclude-genid/configd_create.sh";
				configd:delete "/opt/vyatta/share/tmplscripts/interfaces/dataplane/ipv6/pim/exclude-genid/configd_delete.sh";
			}
		}
	}
	augment /if:interfaces/interfaces-dataplane:dataplane/interfaces-dataplane:vif/interfaces-dataplane:ipv6 {
		container pim {
			presence "true";
			configd:help "Protocol Independent Multicasting (PIM)";
			configd:validate "/opt/vyatta/share/tmplscripts/interfaces/dataplane/vif/ipv6/pim/configd_validate1.cli";
			configd:validate "/opt/vyatta/share/tmplscripts/interfaces/dataplane/vif/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/dataplane/vif/ipv6/pim/propagation-delay/configd_allowed.sh";
				configd:update "/opt/vyatta/share/tmplscripts/interfaces/dataplane/vif/ipv6/pim/propagation-delay/configd_update.sh";
				configd:delete "/opt/vyatta/share/tmplscripts/interfaces/dataplane/vif/ipv6/pim/propagation-delay/configd_delete.sh";
			}
			leaf unicast-bsm {
				type empty;
				configd:help "Enable support for sending and receiving unicast Bootstrap Messages (BSM) on an interface";
				configd:create "/opt/vyatta/share/tmplscripts/interfaces/dataplane/vif/ipv6/pim/unicast-bsm/configd_create.sh";
				configd:delete "/opt/vyatta/share/tmplscripts/interfaces/dataplane/vif/ipv6/pim/unicast-bsm/configd_delete.sh";
			}
			leaf neighbor-filter {
				type string;
				configd:help "Enable filtering of neighbors on the interface";
				configd:allowed "/opt/vyatta/share/tmplscripts/interfaces/dataplane/vif/ipv6/pim/neighbor-filter/configd_allowed.sh";
				configd:update "/opt/vyatta/share/tmplscripts/interfaces/dataplane/vif/ipv6/pim/neighbor-filter/configd_update.sh";
				configd:delete "/opt/vyatta/share/tmplscripts/interfaces/dataplane/vif/ipv6/pim/neighbor-filter/configd_delete.sh";
				configd:validate "/opt/vyatta/share/tmplscripts/interfaces/dataplane/vif/ipv6/pim/neighbor-filter/configd_validate1.cli";
			}
			container state-refresh {
				presence "true";
				configd:help "PIM-DM State Refresh";
				configd:validate "/opt/vyatta/share/tmplscripts/interfaces/dataplane/vif/ipv6/pim/state-refresh/configd_validate1.cli";
				leaf origination-interval {
					type uint32 {
						range 1..100 {
							error-message "Must be between 1-100";
						}
					}
					configd:help "Configure an origination interval value";
					configd:update "/opt/vyatta/share/tmplscripts/interfaces/dataplane/vif/ipv6/pim/state-refresh/origination-interval/configd_update.sh";
					configd:delete "/opt/vyatta/share/tmplscripts/interfaces/dataplane/vif/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/dataplane/vif/ipv6/pim/hello-interval/configd_update.sh";
				configd:delete "/opt/vyatta/share/tmplscripts/interfaces/dataplane/vif/ipv6/pim/hello-interval/configd_delete.sh";
				configd:validate "/opt/vyatta/share/tmplscripts/interfaces/dataplane/vif/ipv6/pim/hello-interval/configd_validate1.cli";
			}
			leaf bsr-border {
				type empty;
				configd:help "Disable bootstrap router (BSR) messages from being sent or received through an interface";
				configd:create "/opt/vyatta/share/tmplscripts/interfaces/dataplane/vif/ipv6/pim/bsr-border/configd_create.sh";
				configd:delete "/opt/vyatta/share/tmplscripts/interfaces/dataplane/vif/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/dataplane/vif/ipv6/pim/mode/configd_allowed.sh";
				configd:update "/opt/vyatta/share/tmplscripts/interfaces/dataplane/vif/ipv6/pim/mode/configd_update.sh";
				configd:delete "/opt/vyatta/share/tmplscripts/interfaces/dataplane/vif/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/dataplane/vif/ipv6/pim/hello-holdtime/configd_update.sh";
				configd:delete "/opt/vyatta/share/tmplscripts/interfaces/dataplane/vif/ipv6/pim/hello-holdtime/configd_delete.sh";
				configd:validate "/opt/vyatta/share/tmplscripts/interfaces/dataplane/vif/ipv6/pim/hello-holdtime/configd_validate1.cli";
				configd:validate "/opt/vyatta/share/tmplscripts/interfaces/dataplane/vif/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/dataplane/vif/ipv6/pim/dr-priority/configd_update.sh";
				configd:delete "/opt/vyatta/share/tmplscripts/interfaces/dataplane/vif/ipv6/pim/dr-priority/configd_delete.sh";
			}
			leaf exclude-genid {
				type empty;
				configd:help "Exclude the GenID (generated ID) option from Hello packets on an interface";
				configd:create "/opt/vyatta/share/tmplscripts/interfaces/dataplane/vif/ipv6/pim/exclude-genid/configd_create.sh";
				configd:delete "/opt/vyatta/share/tmplscripts/interfaces/dataplane/vif/ipv6/pim/exclude-genid/configd_delete.sh";
			}
		}
	}
	augment /if:interfaces/interfaces-l2tpeth:l2tpeth/interfaces-l2tpeth:ipv6 {
		container pim {
			presence "true";
			configd:help "Protocol Independent Multicasting (PIM)";
			configd:validate "/opt/vyatta/share/tmplscripts/interfaces/l2tpeth/ipv6/pim/configd_validate1.cli";
			configd:validate "/opt/vyatta/share/tmplscripts/interfaces/l2tpeth/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/l2tpeth/ipv6/pim/propagation-delay/configd_allowed.sh";
				configd:update "/opt/vyatta/share/tmplscripts/interfaces/l2tpeth/ipv6/pim/propagation-delay/configd_update.sh";
				configd:delete "/opt/vyatta/share/tmplscripts/interfaces/l2tpeth/ipv6/pim/propagation-delay/configd_delete.sh";
			}
			leaf unicast-bsm {
				type empty;
				configd:help "Enable support for sending and receiving unicast Bootstrap Messages (BSM) on an interface";
				configd:create "/opt/vyatta/share/tmplscripts/interfaces/l2tpeth/ipv6/pim/unicast-bsm/configd_create.sh";
				configd:delete "/opt/vyatta/share/tmplscripts/interfaces/l2tpeth/ipv6/pim/unicast-bsm/configd_delete.sh";
			}
			leaf neighbor-filter {
				type string;
				configd:help "Enable filtering of neighbors on the interface";
				configd:allowed "/opt/vyatta/share/tmplscripts/interfaces/l2tpeth/ipv6/pim/neighbor-filter/configd_allowed.sh";
				configd:update "/opt/vyatta/share/tmplscripts/interfaces/l2tpeth/ipv6/pim/neighbor-filter/configd_update.sh";
				configd:delete "/opt/vyatta/share/tmplscripts/interfaces/l2tpeth/ipv6/pim/neighbor-filter/configd_delete.sh";
				configd:validate "/opt/vyatta/share/tmplscripts/interfaces/l2tpeth/ipv6/pim/neighbor-filter/configd_validate1.cli";
			}
			container state-refresh {
				presence "true";
				configd:help "PIM-DM State Refresh";
				configd:validate "/opt/vyatta/share/tmplscripts/interfaces/l2tpeth/ipv6/pim/state-refresh/configd_validate1.cli";
				leaf origination-interval {
					type uint32 {
						range 1..100 {
							error-message "Must be between 1-100";
						}
					}
					configd:help "Configure an origination interval value";
					configd:update "/opt/vyatta/share/tmplscripts/interfaces/l2tpeth/ipv6/pim/state-refresh/origination-interval/configd_update.sh";
					configd:delete "/opt/vyatta/share/tmplscripts/interfaces/l2tpeth/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/l2tpeth/ipv6/pim/hello-interval/configd_update.sh";
				configd:delete "/opt/vyatta/share/tmplscripts/interfaces/l2tpeth/ipv6/pim/hello-interval/configd_delete.sh";
				configd:validate "/opt/vyatta/share/tmplscripts/interfaces/l2tpeth/ipv6/pim/hello-interval/configd_validate1.cli";
			}
			leaf bsr-border {
				type empty;
				configd:help "Disable bootstrap router (BSR) messages from being sent or received through an interface";
				configd:create "/opt/vyatta/share/tmplscripts/interfaces/l2tpeth/ipv6/pim/bsr-border/configd_create.sh";
				configd:delete "/opt/vyatta/share/tmplscripts/interfaces/l2tpeth/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/l2tpeth/ipv6/pim/mode/configd_allowed.sh";
				configd:update "/opt/vyatta/share/tmplscripts/interfaces/l2tpeth/ipv6/pim/mode/configd_update.sh";
				configd:delete "/opt/vyatta/share/tmplscripts/interfaces/l2tpeth/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/l2tpeth/ipv6/pim/hello-holdtime/configd_update.sh";
				configd:delete "/opt/vyatta/share/tmplscripts/interfaces/l2tpeth/ipv6/pim/hello-holdtime/configd_delete.sh";
				configd:validate "/opt/vyatta/share/tmplscripts/interfaces/l2tpeth/ipv6/pim/hello-holdtime/configd_validate1.cli";
				configd:validate "/opt/vyatta/share/tmplscripts/interfaces/l2tpeth/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/l2tpeth/ipv6/pim/dr-priority/configd_update.sh";
				configd:delete "/opt/vyatta/share/tmplscripts/interfaces/l2tpeth/ipv6/pim/dr-priority/configd_delete.sh";
			}
			leaf exclude-genid {
				type empty;
				configd:help "Exclude the GenID (generated ID) option from Hello packets on an interface";
				configd:create "/opt/vyatta/share/tmplscripts/interfaces/l2tpeth/ipv6/pim/exclude-genid/configd_create.sh";
				configd:delete "/opt/vyatta/share/tmplscripts/interfaces/l2tpeth/ipv6/pim/exclude-genid/configd_delete.sh";
			}
		}
	}
	augment /if:interfaces/interfaces-l2tpeth:l2tpeth/interfaces-l2tpeth:vif/interfaces-l2tpeth:ipv6 {
		container pim {
			presence "true";
			configd:help "Protocol Independent Multicasting (PIM)";
			configd:validate "/opt/vyatta/share/tmplscripts/interfaces/l2tpeth/vif/ipv6/pim/configd_validate1.cli";
			configd:validate "/opt/vyatta/share/tmplscripts/interfaces/l2tpeth/vif/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/l2tpeth/vif/ipv6/pim/propagation-delay/configd_allowed.sh";
				configd:update "/opt/vyatta/share/tmplscripts/interfaces/l2tpeth/vif/ipv6/pim/propagation-delay/configd_update.sh";
				configd:delete "/opt/vyatta/share/tmplscripts/interfaces/l2tpeth/vif/ipv6/pim/propagation-delay/configd_delete.sh";
			}
			leaf unicast-bsm {
				type empty;
				configd:help "Enable support for sending and receiving unicast Bootstrap Messages (BSM) on an interface";
				configd:create "/opt/vyatta/share/tmplscripts/interfaces/l2tpeth/vif/ipv6/pim/unicast-bsm/configd_create.sh";
				configd:delete "/opt/vyatta/share/tmplscripts/interfaces/l2tpeth/vif/ipv6/pim/unicast-bsm/configd_delete.sh";
			}
			leaf neighbor-filter {
				type string;
				configd:help "Enable filtering of neighbors on the interface";
				configd:allowed "/opt/vyatta/share/tmplscripts/interfaces/l2tpeth/vif/ipv6/pim/neighbor-filter/configd_allowed.sh";
				configd:update "/opt/vyatta/share/tmplscripts/interfaces/l2tpeth/vif/ipv6/pim/neighbor-filter/configd_update.sh";
				configd:delete "/opt/vyatta/share/tmplscripts/interfaces/l2tpeth/vif/ipv6/pim/neighbor-filter/configd_delete.sh";
				configd:validate "/opt/vyatta/share/tmplscripts/interfaces/l2tpeth/vif/ipv6/pim/neighbor-filter/configd_validate1.cli";
			}
			container state-refresh {
				presence "true";
				configd:help "PIM-DM State Refresh";
				configd:validate "/opt/vyatta/share/tmplscripts/interfaces/l2tpeth/vif/ipv6/pim/state-refresh/configd_validate1.cli";
				leaf origination-interval {
					type uint32 {
						range 1..100 {
							error-message "Must be between 1-100";
						}
					}
					configd:help "Configure an origination interval value";
					configd:update "/opt/vyatta/share/tmplscripts/interfaces/l2tpeth/vif/ipv6/pim/state-refresh/origination-interval/configd_update.sh";
					configd:delete "/opt/vyatta/share/tmplscripts/interfaces/l2tpeth/vif/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/l2tpeth/vif/ipv6/pim/hello-interval/configd_update.sh";
				configd:delete "/opt/vyatta/share/tmplscripts/interfaces/l2tpeth/vif/ipv6/pim/hello-interval/configd_delete.sh";
				configd:validate "/opt/vyatta/share/tmplscripts/interfaces/l2tpeth/vif/ipv6/pim/hello-interval/configd_validate1.cli";
			}
			leaf bsr-border {
				type empty;
				configd:help "Disable bootstrap router (BSR) messages from being sent or received through an interface";
				configd:create "/opt/vyatta/share/tmplscripts/interfaces/l2tpeth/vif/ipv6/pim/bsr-border/configd_create.sh";
				configd:delete "/opt/vyatta/share/tmplscripts/interfaces/l2tpeth/vif/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/l2tpeth/vif/ipv6/pim/mode/configd_allowed.sh";
				configd:update "/opt/vyatta/share/tmplscripts/interfaces/l2tpeth/vif/ipv6/pim/mode/configd_update.sh";
				configd:delete "/opt/vyatta/share/tmplscripts/interfaces/l2tpeth/vif/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/l2tpeth/vif/ipv6/pim/hello-holdtime/configd_update.sh";
				configd:delete "/opt/vyatta/share/tmplscripts/interfaces/l2tpeth/vif/ipv6/pim/hello-holdtime/configd_delete.sh";
				configd:validate "/opt/vyatta/share/tmplscripts/interfaces/l2tpeth/vif/ipv6/pim/hello-holdtime/configd_validate1.cli";
				configd:validate "/opt/vyatta/share/tmplscripts/interfaces/l2tpeth/vif/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/l2tpeth/vif/ipv6/pim/dr-priority/configd_update.sh";
				configd:delete "/opt/vyatta/share/tmplscripts/interfaces/l2tpeth/vif/ipv6/pim/dr-priority/configd_delete.sh";
			}
			leaf exclude-genid {
				type empty;
				configd:help "Exclude the GenID (generated ID) option from Hello packets on an interface";
				configd:create "/opt/vyatta/share/tmplscripts/interfaces/l2tpeth/vif/ipv6/pim/exclude-genid/configd_create.sh";
				configd:delete "/opt/vyatta/share/tmplscripts/interfaces/l2tpeth/vif/ipv6/pim/exclude-genid/configd_delete.sh";
			}
		}
	}
	augment /if:interfaces/interfaces-loopback:loopback/interfaces-loopback:ipv6 {
		container pim {
			presence "true";
			configd:help "Protocol Independent Multicasting (PIM)";
			configd:validate "/opt/vyatta/share/tmplscripts/interfaces/loopback/ipv6/pim/configd_validate1.cli";
			configd:validate "/opt/vyatta/share/tmplscripts/interfaces/loopback/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/loopback/ipv6/pim/propagation-delay/configd_allowed.sh";
				configd:update "/opt/vyatta/share/tmplscripts/interfaces/loopback/ipv6/pim/propagation-delay/configd_update.sh";
				configd:delete "/opt/vyatta/share/tmplscripts/interfaces/loopback/ipv6/pim/propagation-delay/configd_delete.sh";
			}
			leaf unicast-bsm {
				type empty;
				configd:help "Enable support for sending and receiving unicast Bootstrap Messages (BSM) on an interface";
				configd:create "/opt/vyatta/share/tmplscripts/interfaces/loopback/ipv6/pim/unicast-bsm/configd_create.sh";
				configd:delete "/opt/vyatta/share/tmplscripts/interfaces/loopback/ipv6/pim/unicast-bsm/configd_delete.sh";
			}
			leaf neighbor-filter {
				type string;
				configd:help "Enable filtering of neighbors on the interface";
				configd:allowed "/opt/vyatta/share/tmplscripts/interfaces/loopback/ipv6/pim/neighbor-filter/configd_allowed.sh";
				configd:update "/opt/vyatta/share/tmplscripts/interfaces/loopback/ipv6/pim/neighbor-filter/configd_update.sh";
				configd:delete "/opt/vyatta/share/tmplscripts/interfaces/loopback/ipv6/pim/neighbor-filter/configd_delete.sh";
				configd:validate "/opt/vyatta/share/tmplscripts/interfaces/loopback/ipv6/pim/neighbor-filter/configd_validate1.cli";
			}
			container state-refresh {
				presence "true";
				configd:help "PIM-DM State Refresh";
				configd:validate "/opt/vyatta/share/tmplscripts/interfaces/loopback/ipv6/pim/state-refresh/configd_validate1.cli";
				leaf origination-interval {
					type uint32 {
						range 1..100 {
							error-message "Must be between 1-100";
						}
					}
					configd:help "Configure an origination interval value";
					configd:update "/opt/vyatta/share/tmplscripts/interfaces/loopback/ipv6/pim/state-refresh/origination-interval/configd_update.sh";
					configd:delete "/opt/vyatta/share/tmplscripts/interfaces/loopback/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/loopback/ipv6/pim/hello-interval/configd_update.sh";
				configd:delete "/opt/vyatta/share/tmplscripts/interfaces/loopback/ipv6/pim/hello-interval/configd_delete.sh";
				configd:validate "/opt/vyatta/share/tmplscripts/interfaces/loopback/ipv6/pim/hello-interval/configd_validate1.cli";
			}
			leaf bsr-border {
				type empty;
				configd:help "Disable bootstrap router (BSR) messages from being sent or received through an interface";
				configd:create "/opt/vyatta/share/tmplscripts/interfaces/loopback/ipv6/pim/bsr-border/configd_create.sh";
				configd:delete "/opt/vyatta/share/tmplscripts/interfaces/loopback/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/loopback/ipv6/pim/mode/configd_allowed.sh";
				configd:update "/opt/vyatta/share/tmplscripts/interfaces/loopback/ipv6/pim/mode/configd_update.sh";
				configd:delete "/opt/vyatta/share/tmplscripts/interfaces/loopback/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/loopback/ipv6/pim/hello-holdtime/configd_update.sh";
				configd:delete "/opt/vyatta/share/tmplscripts/interfaces/loopback/ipv6/pim/hello-holdtime/configd_delete.sh";
				configd:validate "/opt/vyatta/share/tmplscripts/interfaces/loopback/ipv6/pim/hello-holdtime/configd_validate1.cli";
				configd:validate "/opt/vyatta/share/tmplscripts/interfaces/loopback/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/loopback/ipv6/pim/dr-priority/configd_update.sh";
				configd:delete "/opt/vyatta/share/tmplscripts/interfaces/loopback/ipv6/pim/dr-priority/configd_delete.sh";
			}
			leaf exclude-genid {
				type empty;
				configd:help "Exclude the GenID (generated ID) option from Hello packets on an interface";
				configd:create "/opt/vyatta/share/tmplscripts/interfaces/loopback/ipv6/pim/exclude-genid/configd_create.sh";
				configd:delete "/opt/vyatta/share/tmplscripts/interfaces/loopback/ipv6/pim/exclude-genid/configd_delete.sh";
			}
		}
	}
	augment /if:interfaces/interfaces-openvpn:openvpn/interfaces-openvpn:ipv6 {
		container pim {
			presence "true";
			configd:help "Protocol Independent Multicasting (PIM)";
			configd:validate "/opt/vyatta/share/tmplscripts/interfaces/openvpn/ipv6/pim/configd_validate1.cli";
			configd:validate "/opt/vyatta/share/tmplscripts/interfaces/openvpn/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/openvpn/ipv6/pim/propagation-delay/configd_allowed.sh";
				configd:update "/opt/vyatta/share/tmplscripts/interfaces/openvpn/ipv6/pim/propagation-delay/configd_update.sh";
				configd:delete "/opt/vyatta/share/tmplscripts/interfaces/openvpn/ipv6/pim/propagation-delay/configd_delete.sh";
			}
			leaf unicast-bsm {
				type empty;
				configd:help "Enable support for sending and receiving unicast Bootstrap Messages (BSM) on an interface";
				configd:create "/opt/vyatta/share/tmplscripts/interfaces/openvpn/ipv6/pim/unicast-bsm/configd_create.sh";
				configd:delete "/opt/vyatta/share/tmplscripts/interfaces/openvpn/ipv6/pim/unicast-bsm/configd_delete.sh";
			}
			leaf neighbor-filter {
				type string;
				configd:help "Enable filtering of neighbors on the interface";
				configd:allowed "/opt/vyatta/share/tmplscripts/interfaces/openvpn/ipv6/pim/neighbor-filter/configd_allowed.sh";
				configd:update "/opt/vyatta/share/tmplscripts/interfaces/openvpn/ipv6/pim/neighbor-filter/configd_update.sh";
				configd:delete "/opt/vyatta/share/tmplscripts/interfaces/openvpn/ipv6/pim/neighbor-filter/configd_delete.sh";
				configd:validate "/opt/vyatta/share/tmplscripts/interfaces/openvpn/ipv6/pim/neighbor-filter/configd_validate1.cli";
			}
			container state-refresh {
				presence "true";
				configd:help "PIM-DM State Refresh";
				configd:validate "/opt/vyatta/share/tmplscripts/interfaces/openvpn/ipv6/pim/state-refresh/configd_validate1.cli";
				leaf origination-interval {
					type uint32 {
						range 1..100 {
							error-message "Must be between 1-100";
						}
					}
					configd:help "Configure an origination interval value";
					configd:update "/opt/vyatta/share/tmplscripts/interfaces/openvpn/ipv6/pim/state-refresh/origination-interval/configd_update.sh";
					configd:delete "/opt/vyatta/share/tmplscripts/interfaces/openvpn/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/openvpn/ipv6/pim/hello-interval/configd_update.sh";
				configd:delete "/opt/vyatta/share/tmplscripts/interfaces/openvpn/ipv6/pim/hello-interval/configd_delete.sh";
				configd:validate "/opt/vyatta/share/tmplscripts/interfaces/openvpn/ipv6/pim/hello-interval/configd_validate1.cli";
			}
			leaf bsr-border {
				type empty;
				configd:help "Disable bootstrap router (BSR) messages from being sent or received through an interface";
				configd:create "/opt/vyatta/share/tmplscripts/interfaces/openvpn/ipv6/pim/bsr-border/configd_create.sh";
				configd:delete "/opt/vyatta/share/tmplscripts/interfaces/openvpn/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/openvpn/ipv6/pim/mode/configd_allowed.sh";
				configd:update "/opt/vyatta/share/tmplscripts/interfaces/openvpn/ipv6/pim/mode/configd_update.sh";
				configd:delete "/opt/vyatta/share/tmplscripts/interfaces/openvpn/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/openvpn/ipv6/pim/hello-holdtime/configd_update.sh";
				configd:delete "/opt/vyatta/share/tmplscripts/interfaces/openvpn/ipv6/pim/hello-holdtime/configd_delete.sh";
				configd:validate "/opt/vyatta/share/tmplscripts/interfaces/openvpn/ipv6/pim/hello-holdtime/configd_validate1.cli";
				configd:validate "/opt/vyatta/share/tmplscripts/interfaces/openvpn/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/openvpn/ipv6/pim/dr-priority/configd_update.sh";
				configd:delete "/opt/vyatta/share/tmplscripts/interfaces/openvpn/ipv6/pim/dr-priority/configd_delete.sh";
			}
			leaf exclude-genid {
				type empty;
				configd:help "Exclude the GenID (generated ID) option from Hello packets on an interface";
				configd:create "/opt/vyatta/share/tmplscripts/interfaces/openvpn/ipv6/pim/exclude-genid/configd_create.sh";
				configd:delete "/opt/vyatta/share/tmplscripts/interfaces/openvpn/ipv6/pim/exclude-genid/configd_delete.sh";
			}
		}
	}
	augment /if:interfaces/interfaces-tunnel:tunnel/interfaces-tunnel:ipv6 {
		container pim {
			presence "true";
			configd:help "Protocol Independent Multicasting (PIM)";
			configd:validate "/opt/vyatta/share/tmplscripts/interfaces/tunnel/ipv6/pim/configd_validate1.cli";
			configd:validate "/opt/vyatta/share/tmplscripts/interfaces/tunnel/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/tunnel/ipv6/pim/propagation-delay/configd_allowed.sh";
				configd:update "/opt/vyatta/share/tmplscripts/interfaces/tunnel/ipv6/pim/propagation-delay/configd_update.sh";
				configd:delete "/opt/vyatta/share/tmplscripts/interfaces/tunnel/ipv6/pim/propagation-delay/configd_delete.sh";
			}
			leaf unicast-bsm {
				type empty;
				configd:help "Enable support for sending and receiving unicast Bootstrap Messages (BSM) on an interface";
				configd:create "/opt/vyatta/share/tmplscripts/interfaces/tunnel/ipv6/pim/unicast-bsm/configd_create.sh";
				configd:delete "/opt/vyatta/share/tmplscripts/interfaces/tunnel/ipv6/pim/unicast-bsm/configd_delete.sh";
			}
			leaf neighbor-filter {
				type string;
				configd:help "Enable filtering of neighbors on the interface";
				configd:allowed "/opt/vyatta/share/tmplscripts/interfaces/tunnel/ipv6/pim/neighbor-filter/configd_allowed.sh";
				configd:update "/opt/vyatta/share/tmplscripts/interfaces/tunnel/ipv6/pim/neighbor-filter/configd_update.sh";
				configd:delete "/opt/vyatta/share/tmplscripts/interfaces/tunnel/ipv6/pim/neighbor-filter/configd_delete.sh";
				configd:validate "/opt/vyatta/share/tmplscripts/interfaces/tunnel/ipv6/pim/neighbor-filter/configd_validate1.cli";
			}
			container state-refresh {
				presence "true";
				configd:help "PIM-DM State Refresh";
				configd:validate "/opt/vyatta/share/tmplscripts/interfaces/tunnel/ipv6/pim/state-refresh/configd_validate1.cli";
				leaf origination-interval {
					type uint32 {
						range 1..100 {
							error-message "Must be between 1-100";
						}
					}
					configd:help "Configure an origination interval value";
					configd:update "/opt/vyatta/share/tmplscripts/interfaces/tunnel/ipv6/pim/state-refresh/origination-interval/configd_update.sh";
					configd:delete "/opt/vyatta/share/tmplscripts/interfaces/tunnel/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/tunnel/ipv6/pim/hello-interval/configd_update.sh";
				configd:delete "/opt/vyatta/share/tmplscripts/interfaces/tunnel/ipv6/pim/hello-interval/configd_delete.sh";
				configd:validate "/opt/vyatta/share/tmplscripts/interfaces/tunnel/ipv6/pim/hello-interval/configd_validate1.cli";
			}
			leaf bsr-border {
				type empty;
				configd:help "Disable bootstrap router (BSR) messages from being sent or received through an interface";
				configd:create "/opt/vyatta/share/tmplscripts/interfaces/tunnel/ipv6/pim/bsr-border/configd_create.sh";
				configd:delete "/opt/vyatta/share/tmplscripts/interfaces/tunnel/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/tunnel/ipv6/pim/mode/configd_allowed.sh";
				configd:update "/opt/vyatta/share/tmplscripts/interfaces/tunnel/ipv6/pim/mode/configd_update.sh";
				configd:delete "/opt/vyatta/share/tmplscripts/interfaces/tunnel/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/tunnel/ipv6/pim/hello-holdtime/configd_update.sh";
				configd:delete "/opt/vyatta/share/tmplscripts/interfaces/tunnel/ipv6/pim/hello-holdtime/configd_delete.sh";
				configd:validate "/opt/vyatta/share/tmplscripts/interfaces/tunnel/ipv6/pim/hello-holdtime/configd_validate1.cli";
				configd:validate "/opt/vyatta/share/tmplscripts/interfaces/tunnel/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/tunnel/ipv6/pim/dr-priority/configd_update.sh";
				configd:delete "/opt/vyatta/share/tmplscripts/interfaces/tunnel/ipv6/pim/dr-priority/configd_delete.sh";
			}
			leaf exclude-genid {
				type empty;
				configd:help "Exclude the GenID (generated ID) option from Hello packets on an interface";
				configd:create "/opt/vyatta/share/tmplscripts/interfaces/tunnel/ipv6/pim/exclude-genid/configd_create.sh";
				configd:delete "/opt/vyatta/share/tmplscripts/interfaces/tunnel/ipv6/pim/exclude-genid/configd_delete.sh";
			}
		}
	}
	augment /if:interfaces/interfaces-vti:vti/interfaces-vti:ipv6 {
		container pim {
			presence "true";
			configd:help "Protocol Independent Multicasting (PIM)";
			configd:validate "/opt/vyatta/share/tmplscripts/interfaces/vti/ipv6/pim/configd_validate1.cli";
			configd:validate "/opt/vyatta/share/tmplscripts/interfaces/vti/ipv6/pim/configd_validate2.cli";
			leaf propagation-delay {
				type enumeration {
					enum "1000";
					enum "2000";
					enum "3000";
					enum "4000";
					enum "5000";
				}
				configd:help "Configure a propagation delay value";
				configd:allowed "/opt/vyatta/share/tmplscripts/interfaces/vti/ipv6/pim/propagation-delay/configd_allowed.sh";
				configd:update "/opt/vyatta/share/tmplscripts/interfaces/vti/ipv6/pim/propagation-delay/configd_update.sh";
				configd:delete "/opt/vyatta/share/tmplscripts/interfaces/vti/ipv6/pim/propagation-delay/configd_delete.sh";
			}
			leaf unicast-bsm {
				type empty;
				configd:help "Enable support for sending and receiving unicast Bootstrap Messages (BSM) on an interface";
				configd:create "/opt/vyatta/share/tmplscripts/interfaces/vti/ipv6/pim/unicast-bsm/configd_create.sh";
				configd:delete "/opt/vyatta/share/tmplscripts/interfaces/vti/ipv6/pim/unicast-bsm/configd_delete.sh";
			}
			leaf neighbor-filter {
				type string;
				configd:help "Enable filtering of neighbors on the interface";
				configd:allowed "/opt/vyatta/share/tmplscripts/interfaces/vti/ipv6/pim/neighbor-filter/configd_allowed.sh";
				configd:update "/opt/vyatta/share/tmplscripts/interfaces/vti/ipv6/pim/neighbor-filter/configd_update.sh";
				configd:delete "/opt/vyatta/share/tmplscripts/interfaces/vti/ipv6/pim/neighbor-filter/configd_delete.sh";
				configd:validate "/opt/vyatta/share/tmplscripts/interfaces/vti/ipv6/pim/neighbor-filter/configd_validate1.cli";
			}
			container state-refresh {
				presence "true";
				configd:help "PIM-DM State Refresh";
				configd:validate "/opt/vyatta/share/tmplscripts/interfaces/vti/ipv6/pim/state-refresh/configd_validate1.cli";
				leaf origination-interval {
					type uint32 {
						range 1..100 {
							error-message "Must be between 1-100";
						}
					}
					configd:help "Configure an origination interval value";
					configd:update "/opt/vyatta/share/tmplscripts/interfaces/vti/ipv6/pim/state-refresh/origination-interval/configd_update.sh";
					configd:delete "/opt/vyatta/share/tmplscripts/interfaces/vti/ipv6/pim/state-refresh/origination-interval/configd_delete.sh";
				}
			}
			leaf hello-interval {
				type uint32 {
					range 1..18724 {
						error-message "Must be between 1-18724";
					}
				}
				configd:priority "948";
				configd:help "Configure a hello interval value";
				configd:update "/opt/vyatta/share/tmplscripts/interfaces/vti/ipv6/pim/hello-interval/configd_update.sh";
				configd:delete "/opt/vyatta/share/tmplscripts/interfaces/vti/ipv6/pim/hello-interval/configd_delete.sh";
				configd:validate "/opt/vyatta/share/tmplscripts/interfaces/vti/ipv6/pim/hello-interval/configd_validate1.cli";
			}
			leaf bsr-border {
				type empty;
				configd:help "Disable bootstrap router (BSR) messages from being sent or received through an interface";
				configd:create "/opt/vyatta/share/tmplscripts/interfaces/vti/ipv6/pim/bsr-border/configd_create.sh";
				configd:delete "/opt/vyatta/share/tmplscripts/interfaces/vti/ipv6/pim/bsr-border/configd_delete.sh";
			}
			leaf mode {
				type enumeration {
					enum "sparse" {
						configd:help "Set sparse mode";
					}
					enum "dense" {
						configd:help "Set dense mode";
					}
					enum "sparse-passive" {
						configd:help "Set sparse passive mode";
					}
					enum "dense-passive" {
						configd:help "Set dense passive mode";
					}
				}
				configd:priority "950";
				configd:help "IPv6 PIM mode";
				configd:allowed "/opt/vyatta/share/tmplscripts/interfaces/vti/ipv6/pim/mode/configd_allowed.sh";
				configd:update "/opt/vyatta/share/tmplscripts/interfaces/vti/ipv6/pim/mode/configd_update.sh";
				configd:delete "/opt/vyatta/share/tmplscripts/interfaces/vti/ipv6/pim/mode/configd_delete.sh";
			}
			leaf hello-holdtime {
				type uint32 {
					range 1..65535 {
						error-message "Must be between 1-65535";
					}
				}
				configd:priority "949";
				configd:help "Configure a hello holdtime value";
				configd:update "/opt/vyatta/share/tmplscripts/interfaces/vti/ipv6/pim/hello-holdtime/configd_update.sh";
				configd:delete "/opt/vyatta/share/tmplscripts/interfaces/vti/ipv6/pim/hello-holdtime/configd_delete.sh";
				configd:validate "/opt/vyatta/share/tmplscripts/interfaces/vti/ipv6/pim/hello-holdtime/configd_validate1.cli";
				configd:validate "/opt/vyatta/share/tmplscripts/interfaces/vti/ipv6/pim/hello-holdtime/configd_validate2.cli";
			}
			leaf dr-priority {
				type uint32 {
					range 0..4294967294 {
						error-message "Must be between 0-4294967294";
					}
				}
				configd:help "Set the designated router's priority value";
				configd:update "/opt/vyatta/share/tmplscripts/interfaces/vti/ipv6/pim/dr-priority/configd_update.sh";
				configd:delete "/opt/vyatta/share/tmplscripts/interfaces/vti/ipv6/pim/dr-priority/configd_delete.sh";
			}
			leaf exclude-genid {
				type empty;
				configd:help "Exclude the GenID (generated ID) option from Hello packets on an interface";
				configd:create "/opt/vyatta/share/tmplscripts/interfaces/vti/ipv6/pim/exclude-genid/configd_create.sh";
				configd:delete "/opt/vyatta/share/tmplscripts/interfaces/vti/ipv6/pim/exclude-genid/configd_delete.sh";
			}
		}
	}
}
