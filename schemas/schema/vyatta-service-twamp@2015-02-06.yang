module vyatta-service-twamp {
	namespace "urn:vyatta.com:mgmt:vyatta-service-twamp";
	prefix service-twamp;

	import ietf-inet-types {
		prefix inet;
	}

	import vyatta-types {
		prefix types;
	}
	import vyatta-services {
		prefix service;
	}
	import configd {
		prefix configd;
	}

	organization "Brocade Communications Systems, Inc.";
	contact
		"Brocade Communications Systems, Inc.
		 Postal: 130 Holger Way
		         San Jose, CA 95134
		 E-mail: support@Brocade.com
		 Web: www.brocade.com";
	
	revision 2015-02-06 {
		description "Enforce constraint that client-list prefixes cannot have addresses inconsistent with mask.";
	}

	revision 2014-12-12 {
		description "Initial revision.";
		configd:migration 1;
	}
	
	typedef session-num {
		type uint16 {
			range 1..64 {}
		}
	}
	
	typedef timeout {
		type uint16 {
			range 1..3600 {}
		}
	}

	// Same as types:ip-prefix, but with the restriction that it
	// prefixes cannot have addresses inconsistent with mask
	typedef ip-prefix {
		type union {
			type types:ipv4-prefix {
				configd:syntax "/opt/vyatta/share/tmplscripts/service/twamp/server/client-list/configd_syntax.cli";
			}
			type types:ipv6-prefix {
				configd:syntax "/opt/vyatta/share/tmplscripts/service/twamp/server/client-list/configd_syntax.cli";
			}
		}
	}

	augment /service:service {
		container twamp {
			configd:help "Two-Way Active Measurement Protocol";
			
			container server {
				presence "Signifies the TWAMP server is enabled";
				configd:help "Server configuration";
				configd:end "twampd-config.pl";
				
				leaf-list client-list {
					type ip-prefix;
					configd:help "List of clients that can connect to the server, by default any clients";
				}
				
				leaf-list mode {
					type enumeration {
						enum "no-unauthenticated" {
							configd:help "Disable support for unauthenticated sessions";
						}
						enum "no-mixed" {
							configd:help "Disable support for mixed mode sessions";
						}
						enum "no-authenticated" {
							configd:help "Disable support for authenticated sessions";
						}
						enum "no-encrypted" {
							configd:help "Disable support for encrypted sessions";
						}
					}
					configd:help "TWAMP authentication mode, by default all modes available";
				}
				
				list user {
					key "name";
					leaf name {
						type string {
							length 1..16 {}
						}
						configd:help "User identity";
					}
					leaf password {
						type string {
							length 1..1024 {}
						}
						configd:help "Password used to derive AES key";
						configd:validate "/opt/vyatta/share/tmplscripts/service/twamp/server/user/password/password_validate.cli";
						configd:secret "true";
					}
					configd:validate "/opt/vyatta/share/tmplscripts/service/twamp/server/user/configd_validate.cli";
					configd:help "Configure user for mixed, authenticated and encrypted modes";
				}
				
				leaf maximum-connections {
					type session-num {}
					default "16";
					configd:help "Maximum number of control sessions supported per Twamp server <1-64>, by default 16";
				}
				
				leaf maximum-sessions-per-connection {
					type session-num {}
					default "8";
					configd:help "Maximum number of test sessions per control session <1-64>, by default 8";
				}
				
				leaf server-inactivity-timeout {
					type timeout {}
					default "900";
					configd:help "Control session inactivity timeout in seconds <1-3600>, by default 900";
				}
					
				leaf test-inactivity-timeout {
					type timeout {}
					default "900";
					configd:help "Test session inactivity timeout in seconds <1-3600>, by default 900";
				}
				
				leaf port {
					type inet:port-number {
						range 1..65535 {}
					}
					default "862";
					configd:help "Server TCP port for control session <1-65535>, by default 862";
				}
					
				leaf dscp-value {
					type uint8 {
						range 0..63 {}
					}
					default "0";
					configd:help "Base 10 value of dscp byte in ip header in control packets sent from server <0-63>, by default 0";
				}
			}
		}
	}
}
