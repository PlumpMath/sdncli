module vyatta-system-time {
	namespace "urn:vyatta.com:mgmt:vyatta-system-time";
	prefix system-time;

	import vyatta-system {
		prefix system;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-01-08 {
		description "NTP stats collection";
	}

	revision 2014-12-10 {
		description "IPv6 for NTP";
	}

	revision 2014-08-27 {
		description "Initial revision.";
		configd:migration 1;
	}

	augment /system:system {
		container ntp {
			presence "true";
			configd:priority "300";
			configd:help "Network Time Protocol (NTP) configuration";
			configd:end "/opt/vyatta/share/tmplscripts/system/ntp/configd_end.sh";

			leaf statistics {
				type empty;
				configd:help "Enable statistics collection";
			}
			list server {
				configd:help "Network Time Protocol (NTP) server";
				key "tagnode";
				leaf tagnode {
					type string;
					configd:help "Network Time Protocol (NTP) server";
				}
				leaf preempt {
					type empty;
					configd:help "Specifies the association as preemptable rather than the default persistent";
				}
				leaf dynamic {
					type empty;
					configd:help "Allow server to be configured eve if not reachable";
				}
				leaf noselect {
					type empty;
					configd:help "Marks the server as unused";
				}
				leaf prefer {
					type empty;
					configd:help "Marks the server as preferred";
				}
				leaf address-family {
					type enumeration {
						enum ipv4 {
							configd:help "only IPv4 addresses";
						}
						enum ipv6 {
							configd:help "only IPv6 addresses";
						}
					}
					configd:help "Address family for hostname resolution";
				}
			}
		}
		leaf time-zone {
			type string;
			configd:priority "100";
			configd:help "Local time zone";
			default "GMT";
			configd:update "/opt/vyatta/share/tmplscripts/system/time-zone/configd_update.sh";
			configd:allowed "/opt/vyatta/share/tmplscripts/system/time-zone/configd_allowed.sh";
			configd:end "/opt/vyatta/share/tmplscripts/system/time-zone/configd_end.sh";
			configd:comp_help "/opt/vyatta/share/tmplscripts/system/time-zone/configd_comp_help.txt";
			configd:delete "/opt/vyatta/share/tmplscripts/system/time-zone/configd_delete1.cli";
		}
	}
}
