/***********************************************************************
 * vswitch.yang-: Brocade vswitch Data Model
 *
 * April 2011, Shiv Haris 
 *
 * Copyright (c) 2011 by Brocade Communications Systems, Inc.
 * All rights reserved.
 *
 **********************************************************************/
module brocade-vswitch {

    namespace "urn:brocade.com:mgmt:brocade-vswitch";
    prefix "vswitch";

    import tailf-common {
        prefix tailf;
    }

    import ietf-yang-types {
        prefix yang;
    }

     import ietf-inet-types {
        prefix inet;
     }
		 
    import brocade-common-def {
        prefix common-def;
    }

    import brocade-interface {
       prefix interface;
    }

    organization
         "Brocade Communications Systems, Inc.";

    contact
         "Brocade Communications Systems, Inc.
          Postal: 130 Holger Way
                  San Jose, CA 95134
                   U.S.A
          Tel: +1-408-333-8000
          E-mail: support@Brocade.com
          web: www.brocade.com.";

    description
         "This management submodule is an instrumentation to 
          manage Virtual switch features.";

    revision "2011-04-18" {
        description
           "Initial version of the management submodule vswitch.";
    }

    typedef vinterface-type {
        type enumeration {
            enum vm-interface {
                value 11;
            }
            enum console-interface {
                value 12;
            }
            enum vmkernel-interface {
                value 13;
            }
        }
    }

    
    typedef vcenter-url {
        type string {
            pattern '[h][t][t][p]([s]{0,1})[:][/][/]([-a-zA-Z0-9\.\\\\@#\+\*\(\)=\{~\}%<>=$_:\[\]\|]{1,57})';
            length "1 .. 64" {
                error-message "URL length should be in the range 1-64";
            }
        }
    }
    
    typedef vnetwork-log-size {
        type uint8 {
            range "1..10" {
            }

        }
        units "Megabyte";
    }
    
    typedef vnetwork-log-count {
        type uint8 {
            range "1..10" {
            }

        }
    }

    
    grouping last-rcvd-record-info {
        leaf last-rcvd-instance {
            type uint32;
            mandatory false;
            description "Last received record. 0 means this is the first request";
        }
    }

    grouping records-info {
        leaf has-more {
            type boolean;
        }

        leaf instance-id {
            type uint32;
        }
    }

    /* RPC's are added for netconf support */
    rpc get-vnetwork-hosts {
        description "Shows discovered hosts";
        input {
                leaf vcenter {
                    type string {
                        length "1..80";
                    }
                    mandatory true;
                    description "vCenter name";
                }
                leaf datacenter {
                    type string {
                        length "1..80";
                    }
                    mandatory false;
                    description "datacenter name";
                }
                leaf name {
                    type string {
                        length "1..80";
                    }
                    mandatory false;
                    description "Host name";
                }
                leaf last-rcvd-instance {
                    type uint32;
                    mandatory false;
                    description "Last received record. 0 means this is the first request";
                }
			}

        output {
            list vnetwork-hosts {
                leaf name {
                    type string;
                    description "host name";
                }
                leaf vmnic {
                    type string;
                    description "host NIC";
                }
				leaf datacenter {
					type string;
					description "host datacenter";
				}
                leaf mac {
                    type yang:mac-address;
                    description "vmnic Mac address in HH:HH:HH:HH:HH:HH format";
                }
                leaf vswitch {
                    type string;
                    description "regular or distributed virtual switch";
                }
                uses interface:interface-name-info;
            }            
            uses records-info {
                description
                    "Indicates if there are more instances; client
                     can retrieve them by invoking the rpc again with
                     the last record information.";
            }

        }
    }

    rpc get-vnetwork-vms {
        description "Shows discovered VMs";
        input {
                leaf name {
                    type string {
                        length "1..80";
                    }
                    mandatory false;
                    description "Virtual machine name";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vnetwork-vms {
                leaf name {
                    type string;
                    description "virtual machine name";
                }
                leaf mac {
                    type yang:mac-address;
                    description "vnic Mac address in HH:HH:HH:HH:HH:HH format";
                }
                leaf datacenter {
                    type string;
                    description "host datacenter";
                }
                leaf ip {
                    type string;
                    description "vnic IP address";
                }
                leaf host-nn {
                    type string;
                    description "host name";
                }
            }
            uses records-info {
                description
                    "Indicates if there are more instances; client
                     can retrieve them by invoking the rpc again with
                     the last record information.";
            }
        }
    }

    rpc get-vnetwork-dvpgs {
        description "Shows discovered distributed virtual port-groups";
        input {
                leaf name {
                    type string {
                        length "1..80";
                    }
                    mandatory false;
                    description "Distributed virtual port-group name";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vnetwork-dvpgs {
                leaf name {
                    type string;
                    description "port group name";
                }
                leaf datacenter {
                    type string;
                    description "host datacenter";
                }
                leaf dvs-nn {
                    type string;
                    description "distributed virtual switch";
                }
                leaf vlan {
                    type string;
                    description "allowed vlans";
               }
            }
            uses records-info {
                description
                    "Indicates if there are more instances; client
                     can retrieve them by invoking the rpc again with
                     the last record information.";
            }
        }
    }

    rpc get-vnetwork-dvs {
        description "Shows discovered Distributed Virtual Switches";
        input {
                leaf name {
                    type string {
                        length "1..80";
                    }
                    mandatory false;
                    description "Distributed virutal switch name";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vnetwork-dvs {
                leaf name {
                    type string;
                    description "distributed virtual switch name";
                }
                leaf host {
                    type string;
                    description "host name";
                }
                leaf datacenter {
                    type string;
                    description "host datacenter";
                }
                leaf pnic {
                    type string;
                    description "host NIC";
                }
                uses interface:interface-name-info;
            }
            uses records-info {
                description
                    "Indicates if there are more instances; client
                     can retrieve them by invoking the rpc again with
                     the last record information.";
            }
        }
    }

    rpc get-vnetwork-vswitches {
        description "Shows discovered Virtual Switches";
        input {
                leaf name {
                    type string {
                        length "1..80";
                    }
                    mandatory false;
                    description "Virtual switch name";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vnetwork-vswitches {
                leaf name {
                    type string;
                    description "virtual switch name";
                }
                leaf host {
                    type string;
                    description "host name";
                }
                leaf datacenter {
                    type string;
                    description "host datacenter";
                }
                leaf pnic {
                    type string;
                    description "host NIC";
               }
                uses interface:interface-name-info;
            }
            uses records-info {
                description
                    "Indicates if there are more instances; client
                     can retrieve them by invoking the rpc again with
                     the last record information.";
            }
        }
    }

    rpc get-vnetwork-portgroups {
        description "Shows discovered PortGroups";
        input {
                leaf name {
                    type string  {
                        length "1..80";
                    }
                    mandatory false;
                    description "Port group name";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vnetwork-pgs {
                leaf name {
                    type string;
                    description "port group name";
                }
                leaf datacenter {
                    type string;
                    description "host datacenter";
                }
                leaf vs-nn {
                    type string;
                    description "virtual switch name";
                }
                leaf vlan {
                    type string;
                    description "allowed vlans";
                }
                leaf host-nn {
                    type string;
                    description "host name";    
               }
            }
            uses records-info {
                description
                    "Indicates if there are more instances; client
                     can retrieve them by invoking the rpc again with
                     the last record information.";
            }
        }
    }

    rpc get-vmpolicy-macaddr {
        description "Shows vnics/vmknics to portgroup to port-profile association";
        input {
                leaf mac {
                    type yang:mac-address;
                    description "Mac address in HH:HH:HH:HH:HH:HH format";
                }
                leaf vcenter {
                    type string {
                        length "1..80";
                    }
                    mandatory true;
                    description "vCenter name";
                }
                leaf datacenter {
                    type string {
                        length "1..80";
                    }
                    mandatory false;
                    description "datacenter name";
                }
                leaf last-rcvd-instance {
                    type uint32;
                    mandatory false;
                    description "Last received record. 0 means this is the first request";
                }
        }
        output {
            list vmpolicy-macaddr {
                leaf mac {
                    type yang:mac-address; 
                    description "vnic Mac address in HH:HH:HH:HH:HH:HH format";
                }
                leaf name {
                    type string;
                    description "virutal machine name";
                }
                leaf datacenter {
                    type string;
                    description "host datacenter";
                }
                leaf dvpg-nn {
                    type string;
                    description "distributed virtual port group";
                }
                leaf port-nn {
                    type string;
                    description "vm port ID";
                }
                leaf port-prof {
                    type string;
                    description "port profile";
                }
            }
            uses records-info {
                description
                    "Indicates if there are more instances; client
                     can retrieve them by invoking the rpc again with
                     the last record information.";
            }
        }
    }
    
    augment "/common-def:show" {

        /* tailf:action is used for cli support */
        container vnetwork {
            description "Shows virtual infrastructure information";
      tailf:action datacenter {
                description "Shows discovered datacenters";
                input {
                        leaf vcenter {
                            type string {
                               length "1..80";
                            }
                            mandatory true;
                            description "vCenter name";
                        }
                    choice op {
                        leaf id {
                            type string {
                               length "1..80";
                            }
                            mandatory false;
                            description "Datacenter id";
                        }
                    }                      
              }
      }

      tailf:action hosts {
                description "Shows discovered hosts";
                input {
                        leaf vcenter {
                            type string {
                               length "1..80";
                            }
                            mandatory true;
                            description "vCenter name";
                        }
                        leaf datacenter {
                            type string {
                               length "1..80";
                            }
                            mandatory false;
                            description "Datacenter id";
                        }
                
                    choice op {
                        leaf name {
                            type string {
                               length "1..80";
                            }
                            mandatory false;
                            description "Host name";
                        }
                    }
                }
                output {
                    list vnetwork-hosts {
                        leaf name {
                            type string;
                            description "host name";
                        }
                        leaf vmnic {
                            type string;
                            description "host NIC";
                        }
                        leaf mac {
                            type yang:mac-address;
                            description "vmnic Mac address in HH:HH:HH:HH:HH:HH format";
                        }
                        leaf vswitch {
                            type string;
                            description "regular or distributed virtual switch";
                        }
                        uses interface:interface-name-info;
                    }
                }
            }
            tailf:action vms {
                description "Shows discovered VMs";
                input {
                        leaf vcenter {
                            type string {
                               length "1..80";
                            }
                            mandatory true;
                            description "vCenter name";
                        }
                        leaf datacenter {
                            type string {
                               length "1..80";
                            }
                            mandatory false;
                            description "Datacenter id";
                        }
                   choice op {
                        leaf name {
                            type string {
                               length "1..80";
                            }
                            mandatory false;
                            description "Virtual machine name";
                        }
                    }
                }
                output {
                    list vnetwork-vms {
                        leaf name {
                            type string;
                            description "virtual machine name";
                        }
                        leaf mac {
                            type yang:mac-address;
                            description "vnic Mac address in HH:HH:HH:HH:HH:HH format";
                        }
                        leaf ip {
                            type inet:ip-address;
                            description "vnic IP address";
                        }
                        leaf host-nn {
                            type string;
                            description "host name";
                        }
                    }
                }
            }
            tailf:action dvpgs {
                description
                    "Shows discovered distributed virtual port-groups";
                input {
                        leaf vcenter {
                            type string {
                               length "1..80";
                            }
                            mandatory true;
                            description "vCenter name";
                        }
                        leaf datacenter {
                            type string {
                               length "1..80";
                            }
                            mandatory false;
                            description "Datacenter id";
                        }
                    choice op {
                        leaf name {
                            type string  {
                               length "1..80";
                            }
                            mandatory false;
                            description 
                                "Distributed virtual port-group name";
                        }
                    }
                }
                output {
                    list vnetwork-dvpgs {
                        leaf name {
                            type string;
                            description "port group name";
                        }
                        leaf dvs-nn {
                            type string;
                            description "distributed virtual switch";
                        }
                        leaf vlan {
                            type string;
                            description "allowed vlans";
                       }
                    }
                }
            }
            tailf:action dvs {
                description 
                    "Shows discovered distributed virtual switches";
                input {
                        leaf vcenter {
                            type string {
                               length "1..80";
                            }
                            mandatory true;
                            description "vCenter name";
                        }
                        leaf datacenter {
                            type string {
                               length "1..80";
                            }
                            mandatory false;
                            description "Datacenter id";
                        }
                    choice op {
                        leaf name {
                            type string  {
                               length "1..80";
                            }
                            mandatory false;
                            description 
                                "Distributed virutal switch name";
                        }
                    }
                }
                output {
                    list vnetwork-dvs {
                        leaf name {
                            type string;
                            description 
                                "distributed virtual switch name";
                        }
                        leaf host {
                            type string;
                            description "host name";
                        }
                        leaf pnic {
                            type string;
                            description "host NIC";
                        }
                        uses interface:interface-name-info;
                    }
                }

            }
            tailf:action vss {
                description "Shows discovered standard virtual switches";
                input {
                        leaf vcenter {
                            type string {
                               length "1..80";
                            }
                            mandatory true;
                            description "vCenter name";
                        }
                        leaf datacenter {
                            type string {
                               length "1..80";
                            }
                            mandatory false;
                            description "Datacenter id";
                        }
                    choice op {
                        leaf name {
                            type string {
                               length "1..80";
                            }
                            mandatory false;
                            description "Virtual switch name";
                        }
                    }
                }
                output {
                    list vnetwork-vswitches {
                        leaf name {
                            type string;
                            description "virtual switch name";
                        }
                        leaf host {
                            type string;
                            description "host name";
                        }
                        leaf pnic {
                            type string;
                            description "host NIC";
                        }
                        uses interface:interface-name-info;
                    }
                }
            }
            tailf:action pgs {
                description "Shows discovered standard port-groups";
                input {
                        leaf vcenter {
                            type string {
                               length "1..80";
                            }
                            mandatory true;
                            description "vCenter name";
                        }
                        leaf datacenter {
                            type string {
                               length "1..80";
                            }
                            mandatory false;
                            description "Datacenter id";
                        }
                    choice op {
                        leaf name {
                            type string {
                               length "1..80";
                            }
                            mandatory false;
                            description "Port group name";
                        }
                    }
                }
                output {
                    list vnetwork-pgs {
                        leaf name {
                            type string;
                            description "port group name";
                        }
                        leaf vs-nn {
                            type string;
                            description "virtual switch name";
                        }
                        leaf vlan {
                            type string;
                            description "allowed vlans";
                        }
                        leaf host-nn {
                            type string;
                            description "host name";
                       }
                    }
                }

            }
            container vmpolicy {
                description "Shows vnics/vmknics to portgroup to port-profile association";
                tailf:action macaddr {
                    description "Show MAC address policies";
                    input {
                        leaf vcenter {
                            type string {
                               length "1..80";
                            }
                            mandatory true;
                            description "vCenter name";
                        }
                        leaf datacenter {
                            type string {
                               length "1..80";
                            }
                            mandatory false;
                            description "Datacenter id";
                        }
                        choice op {
                            leaf mac {
                                type yang:mac-address;
                                description "Mac address in HH:HH:HH:HH:HH:HH format";
                            }
                        }
                    }
                    output {
                        list vmpolicy-macaddr {
                            leaf mac {
                                type yang:mac-address;
                                description "vnic Mac address in HH:HH:HH:HH:HH:HH format";
                            }
                            leaf name {
                                type string;
                                description "virutal machine name";
                            }
                            leaf dvpg-nn {
                                type string;
                                description 
                                "distributed virtual port group";
                            }
                            leaf port-nn {
                                type string;
                                description "vm port ID";
                            }
                            leaf port-prof {
                                type string;
                                description "port profile";
                            }
                        }
                    }
                }
            }
        }
    }

    

    list vcenter {
        key id;
        description "vCenter";
        leaf id {
            type common-def:name-string32;
			description "NAME;;vCenter name (Max Size - 32)";
        }
		
		
		container credentials
		{
			
			leaf url {
				type vcenter-url;
				description "URL";
			}
			leaf username {
                type string {
                    length "1 .. 255" {
                        error-message "Username length should be in the range 1-255";
                    }
                }
				description "User name";
			}
			leaf password {
				type string {
                }
				description "Password";
			}
		}
		
		leaf activate {
            type empty;
			description "Activate the vCenter discovery";
        }
        
        leaf interval {
            type uint32 {
                range "0..1440" {
                }
            }
            units "Minutes";
            description "Discovery Timer Interval";
        }

        container discovery {


            container ignore-delete-all-response
            {

            leaf ignore-value {
            type uint32 {
                range "0..9999" {
                }
            }
            }

            leaf always {
            type empty;
            description "Always ignore delete-all from vCenter";
            }

            description "Ignore delete-all from vCenter";

        }

    }


    }           
}
