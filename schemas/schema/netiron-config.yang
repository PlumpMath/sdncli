// YANG module for Netiron configuration definitions.
// Revisions:
//     2011-04-20: Initial version.
//

module netiron-config 
{
    namespace "http://brocade.com/ns/netconf/config/netiron-config/";
    prefix "brcd";

    include common-defs;
    include vlan-config;
    include interface-config;
    include mpls-config;

    organization
    	"Brocade Communications Inc.";

    contact
             "Technical Support Center"+
             "130 Holger Way,"+
             "San Jose, CA  95134"+
             "Email:  ipsupport@brocade.com"+
             "Phone: 1-800-752-8061"+
             "URL:  www.brocade.com";

    description
    	"NetIron Config module. VERSION: V5.8.00a";
    
    revision 2011-04-20
    {
    	description "Initial revision";
    }
    
    grouping netiron-config
    {
        description "NetIron configuration group";
        container netiron-config
        {
            description "NetIron configuration";
            uses vlan-config-grouping;
            uses interface-config-grouping;
            uses mpls-config-grouping;
        }
    }
}
