/***********************************************************************
 * brocade-ras.yang: Brocade RAS Data model
 *
 * April 2011,Rajni Balasubramanian
 *
 * Copyright (c) 2011-2012 by Brocade Communications Systems, Inc.
 * All rights reserved.
 *
 **********************************************************************/
module brocade-ras {
  namespace "urn:brocade.com:mgmt:brocade-ras";
  prefix "ras";

  import ietf-inet-types {
	prefix inet;
  }

  import tailf-common {
    prefix tailf;
  }

  import brocade-common-def {
	prefix common-def;
  }

  organization
      "Brocade Communications Systems, Inc.";

  contact           
      "Brocade Communications Systems, Inc.
       Postal: 130 Holger Way
               San Jose, CA 95134
                U.S.A
       Tel: +1-408-333-8000
       E-mail: support@Brocade.com 
       web: www.brocade.com.";

  description      
      "This management module is an instrumentation to log collection 
        like supportsave,copy support and USB management";

  revision "2011-04-11" {
      description     
          "Initial version of this management module.";
    }




/* for user defined data-types */
/* include brocade-common-def; */

  typedef switchidType {
        type string {
           length 1..3 {
	          error-message "Invalid rbridge-id (must be in the range 1 - 239) or all";
           }
        }
  }

  typedef switchidType-noall {
        type string {
           length 1..3 {
	          error-message "Invalid rbridge-id (must be in the range 1 - 239)";
           }
        }
  }

	typedef timeout-value {
		type uint32 {
			range 2..5 {
				error-message "Invalid Timeout (must be in range 2-5)";
           }
        }
  }
	typedef directory-path {
		type string {
			length 1..256 {
				error-message "Enter Valid path with length not more than 256 charecters";
			}
		}
	}

	typedef rbridge-ids-all-type {
		description
			"The unique identifier for a switch.  The usage of `all'
			refers to `all' rbridge-id's in the cluster.";
		type union {
			type common-def:ui32-range;
			type string {
				pattern "all";
			}
		}
	}

grouping copy-support-ftp-scp-parameters {
    leaf user {
        type string;
        mandatory true;
    }
    leaf host {
        type string;
        mandatory true;
    }
    leaf directory {
        type directory-path;
        mandatory true;
    }
    leaf password {
        type string;
        mandatory false;
    }
    leaf rbridge-id{
		type rbridge-ids-all-type;
        mandatory false;
    }
	leaf timeout {
		type timeout-value;
		mandatory false;
	}
	leaf module {
		type string;
		mandatory false;
	}
	leaf linecard {
		type string;
		mandatory false;
	}
	leaf group {
		type string;
		mandatory false;
	}
}

typedef copy-support-status {
    type enumeration {
        enum success {
            value 0;
        }
        enum failed {
            value 1;
        }
    }
}

grouping copy-support-ftp-scp-output {
    list supportSaveResult {
        key rbridge-id;
        leaf rbridge-id{
            type switchidType;
            mandatory true;
        }

        leaf status-code {
            type copy-support-status;
            mandatory true;
        }

        leaf status-str {
            type string;
            mandatory false;
        }
    }
}

container copy {
    container support {
        tailf:action ftp {
            input {
			    uses copy-support-ftp-scp-parameters;
            }
            output {
                uses copy-support-ftp-scp-output;
            }
        }

        tailf:action scp {
            input {
			    uses copy-support-ftp-scp-parameters;
            }
            output {
                uses copy-support-ftp-scp-output;
            }
        }

        tailf:action usb {
            input {
                leaf directory {
                    type string;
                    mandatory true;
                }
				leaf rbridge-id{
					type rbridge-ids-all-type;
                    mandatory false;
                }
				leaf timeout {
					type timeout-value;
					mandatory false;
				}
				leaf module {
					type string;
					mandatory false;
				}
            }
            output {
                uses copy-support-ftp-scp-output;
            }
        }
    
	}
	
	tailf:action support-interactive {
		input {}
		output {
			leaf result {
				type string;
			}
		}
	}
}

typedef audit-class {
	type enumeration {
		enum SECURITY {
			value 1;
		}
		enum CONFIGURATION {
			value 2;
		}
		enum FIRMWARE {
			value 3;
		}
/*
		// As of now, not in use
		enum ALL {
			value 10;
		}
*/
	}
}

typedef raslog-console {
	type enumeration {
		enum INFO {
			value 1;
		}
		enum ERROR {
			value 2;
		}
		enum WARNING {
			value 3;
		}
		enum CRITICAL {
			value 4;
		}
	}
}

typedef message-severity {
	type enumeration {
		enum INFO {
			value 1;
		}
		enum ERROR {
			value 2;
		}
		enum WARNING {
			value 3;
		}
		enum CRITICAL {
			value 4;
		}
		enum DEFAULT {
			value 5;
		}
	}
}

typedef facility-enum {
    type enumeration {
        enum LOG_LOCAL0 {
            value 0;
        }
        enum LOG_LOCAL1 {
            value 1;
        }
        enum LOG_LOCAL2 {
            value 2;
        }
        enum LOG_LOCAL3 {
            value 3;
        }
        enum LOG_LOCAL4 {
            value 4;
        }
        enum LOG_LOCAL5 {
            value 5;
        }
        enum LOG_LOCAL6 {
            value 6;
        }
        enum LOG_LOCAL7 {
            value 7;
        }
    }
}

typedef iptype-enum {
    type enumeration {
        enum MM_IP{
            value 0;
        }
        enum CHASSIS_IP{
            value 1;
        }
	}
}

container logging {
  container raslog {
	  container message {
		list msgId {
			key "msgId";
			leaf msgId {
				type string;
			}
			leaf severity {
				type message-severity;
			}
			leaf suppress {
				type empty;
			}
			leaf syslog {
				type empty;
			}
		}
	  }
	  container module {
		list modId {
			key "modId";
			leaf modId {
				type string;
			}
		}
	 }
	  leaf console {
		type raslog-console;
	  }
	}

    list syslog-server {
      key "syslogip";
      leaf syslogip {
   	  type inet:ip-address;
      }
      leaf secure {
   	    type empty;
        mandatory false;
      }
      leaf port {
        type uint16 {
			range "0 .. 65535" {
				error-message "Error : Port Number must be in the range 0 - 65535";
			}
		}
        default 514;
      }
    }

    container auditlog {
      list class {
        max-elements 3;
        key "class";
        leaf class {
	    type audit-class;
        }
      }
    }
     container syslog-facility {
        leaf local {
            type facility-enum;
        }
    }
     container syslog-client {
        leaf localip {
            type iptype-enum;
			mandatory true;
        }
    }

}

container destination_console {
	container logging {
		container raslog {
			tailf:action console {
				input {
					choice ras-con {
						case stop {
							leaf stop {
								type uint32{
									range "1..120"
									{
										error-message "Minutes must be in the range 1 - 120";
									}
								}
								mandatory true;
							}
						}
						case start {
							leaf start {
								type empty;
								mandatory false;
							}
						}
					}
					leaf rbridge-id {
						type switchidType;
						mandatory false;
					}
				}
			}
		}
	}
}

container system {
	container usb {
		tailf:action on {
			input {
				leaf rbridge-id{

					type switchidType;
					mandatory false;
				}
			}
		}
		tailf:action off {
			input {
				leaf rbridge-id{
					type switchidType;
					mandatory false;
				}
			}
		}
		tailf:action dir {
			input {
				leaf rbridge-id{
					type switchidType;
					mandatory false;
				}
			}
		}
		tailf:action remove {
			input {
				leaf directory {
					type string;
					mandatory true;
				}
				leaf file {
					type string;
					mandatory true;
				}
				leaf rbridge-id{
					type switchidType;
					mandatory false;
				}
			}
		}
	}
	container switch-attributes {
		list rbridge-id{
			key "rbridge-id";
			leaf rbridge-id{
				type switchidType-noall;
			}
			leaf chassis-name {
				type string {
				   length 1..30 {
			   		}
				}
			}
			leaf host-name {
				type string {
				   length 1..30 {
			   		}
				}
			}
		}
		leaf chassis-name {
			type string {
				length 1..30 {
				}
			}
		}
		leaf host-name {
			type string {
				length 1..30 {
				}
			}
		}
	}
}

typedef cmd-status {
    type enumeration {
        enum unknown {
            value 1;
        }
        enum completed {
            value 2;
        }
        enum in-progress {
            value 3;
        }
        enum error {
            value 4;
        }
    }
}

rpc bna-config-cmd {
    description "copy configuration data to/from system. This is a non-blocking command, the caller needs to query for the command completion status using the session-id returned.";
    input {
        leaf src {
            description "ftp/scp URL/running-config/startup-config/default-config";
            type string;
            mandatory true;
        }
        leaf dest {
            type string;
            description "ftp/scp URL/running-config/startup-config";
            mandatory true;
        }
    }
    output {
        leaf session-id {
            type uint32;
            mandatory true;
        }
        leaf status {
            type cmd-status;
            mandatory true;
        }
        leaf status-string {
            description "Error in string format";
            type string;
            mandatory false;
        }
    }
}

rpc bna-config-cmd-status {
    description "Query the status of a previous config-cmd";
    input {
        leaf session-id {
            type uint32;
            mandatory true;
        }
    }
    output {
        leaf status {
            type cmd-status;
            mandatory true;
        }
        leaf status-string {
            description "Error in string format";
            type string;
            mandatory false;
        }
    }
}

container support {
	  container autoupload-param {
		leaf hostip {
			type inet:ip-address;
			mandatory true;
		}
		leaf username {
			type string;
			mandatory true;
		}
		leaf directory {
			type string {
				length "1..47" {
					error-message "Enter valid path with length not more than 47 characters.";
				}
			}
			mandatory true;
		}
		leaf protocol {
			type string {
				length "3..4";
				pattern 'ftp|scp|sftp|FTP|SCP|SFTP' {
					error-message "Error: Invalid Protocol. Please use one of the following: ftp, scp, sftp.";
				}
			}
			mandatory true;
		}
		leaf password {
			type string;
			mandatory false;
		}
	}

	container support-param {
		leaf hostip {
			type inet:ip-address;
			mandatory true;
		}
		leaf username {
			type string;
			mandatory true;
		}
		leaf directory {
			type string;
			mandatory true;
		}
		leaf protocol {
			type string {
				length "3..4";
				pattern 'ftp|scp|sftp|FTP|SCP|SFTP' {
					error-message "Error: Invalid Protocol. Please use one of the following: ftp, scp, sftp.";
				}
			}
			mandatory true;
		}
		leaf password {
			type string;
			mandatory false;
		}
	}
		container autoupload {
			leaf enable {
				type empty;
			}
		}

	leaf ffdc {
		type empty;
		description "FFDC operation";
	}
}

container logtest {
    container raslog {
		tailf:action gmsg {
		    input {
				leaf messageID {
					type string {
						length 6..9 {
						}
					}
				}
			}
		}
   }
}

container auditlog {
	tailf:action gmsg {
		input {
			leaf messageID {
			type string {
		    length 6..9 {
			}
			}
		}
	}
	}
}

container resource-monitor {
	tailf:action memory {
		input {
			choice srm {
				case enable {
					leaf enable {
						type empty;
					}
				}
				case disable {
					leaf disable {
						type empty;
					}
				}
			}
		}
	}
	tailf:action cpu {
		input {
			choice srm {
				case enable {
					leaf enable {
						type empty;
					}
				}
				case disable {
					leaf disable {
						type empty;
					}
				}
			}
		}
	}
}

}
