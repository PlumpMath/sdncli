/***********************************************************************
 * brocade-dhcp.yang: Brocade YANG data model for DHCP configuration.
		 			  Currently supports basic relay agent functionality
 *					  only.
 *
 * May 2013, Aparna Kuppachi
 *
 * Copyright (c) 2013 by Brocade Communications Systems, Inc.
 * All rights reserved.
 *
 **********************************************************************/

module brocade-dhcp {
    namespace "urn:brocade.com:mgmt:brocade-dhcp";
    prefix dhcp;

    /* Linkage Statements */

    import brocade-rbridge {
        prefix rbridge;
    }

    import brocade-interface {
        prefix interface;
    }

    import brocade-ip-config {
        prefix ip-config;
    }

    import brocade-common-def {
        prefix common-def;
    }

    import tailf-common {
        prefix "tailf";
    }

    import ietf-inet-types {
        prefix "inet";
    }

    /* Meta Information */
    
    organization
        "Brocade Communications Systems, Inc.";

    contact           
        "Brocade Communications Systems, Inc.
         Postal: 130 Holger Way,
                 San Jose, CA 95134 
                  U.S.A
         Tel: +1-408-333-8000
         E-mail: support@Brocade.com 
         web: www.brocade.com.";

    description       
        "This management module is an instrumentation to manage 
         DHCP functionality."; 

    /* Revision history */
        
    revision "2013-05-20" {
        description     
            "Initial version of this management module.";
    }

    /* Module Definition */

    typedef dhcp-ipv4-address {
        type inet:ipv4-address {
        }    
    }       


    grouping interface-fo-dhcp {
        container interface-fo-dhcp-conf {
            //tailf:callpoint DHCPRelayPhyInterfaceCallPoint;
            uses interface-dhcp {
				refine "dhcp/relay" {
				}
				refine "dhcp/relay/servers" {
				}
			}
        }
    }

    grouping interface-hu-dhcp {
        container interface-hu-dhcp-conf {
            //tailf:callpoint DHCPRelayPhyInterfaceCallPoint;
            //uses interface-dhcp;
            uses interface-dhcp {
				refine "dhcp/relay" {
				}
				refine "dhcp/relay/servers" {
				}
			}
        }
    }

    grouping interface-te-dhcp {
        container interface-te-dhcp-conf {
            //tailf:callpoint DHCPRelayPhyInterfaceCallPoint;
            //uses interface-dhcp;
            uses interface-dhcp {
				refine "dhcp/relay" {
				}
				refine "dhcp/relay/servers" {
				}
			}
        } 
    }

    grouping interface-gi-dhcp {
        container interface-gi-dhcp-conf {
            //tailf:callpoint DHCPRelayPhyInterfaceCallPoint;
            //uses interface-dhcp;
            uses interface-dhcp {
				refine "dhcp/relay" {
				}
				refine "dhcp/relay/servers" {
				}
			}
        }
    }

    grouping interface-ve-dhcp {
        container interface-ve-dhcp-conf {
            //tailf:callpoint DHCPRelayVeInterfaceCallPoint;
            //uses interface-dhcp;
            uses interface-dhcp {
				refine "dhcp/relay" {
				}
				refine "dhcp/relay/servers" {
				}
			}
        }
    }


    grouping interface-dhcp {
        container dhcp {
        	container relay {

            	list servers {
					key "relay-ip-addr server-vrf-name" ;
					max-elements 16;   /* Currently upto 16 relay addresses supported per interface */

					leaf relay-ip-addr {
                		type dhcp-ipv4-address;
						description "DHCP server IP address";
					}

					leaf server-vrf-name {
                        type common-def:vrf-name;
						description "Name of the VRF that the DHCP server is within";
					}
            	}

				leaf gateway {
					description "Gateway address";
					type dhcp-ipv4-address;
				}
			} /* interface/ip/dhcp/relay */
        } /* interface/ip/dhcp */
    } /* grouping interface-dhcp */
   
    grouping dhcp-cmds {
        container dhcp {

            container relay {

                    container information {

                        leaf option {
                            description "DHCP Relay Information Option";
                            type empty;
                        }
                    }
                }
            }
    }

    augment "/rbridge:rbridge-id/rbridge:ip" {
        uses dhcp-cmds;
    }

    augment "/rbridge:rbridge-id/interface:interface/interface:ve/ip-config:ip" {
        uses interface-ve-dhcp;
    }

    augment "/interface:interface/interface:fortygigabitethernet/interface:ip" {
        uses interface-fo-dhcp;
    }

    augment "/interface:interface/interface:hundredgigabitethernet/interface:ip" {
        uses interface-hu-dhcp;
    }

    augment "/interface:interface/interface:tengigabitethernet/interface:ip" {
        uses interface-te-dhcp;
    }

    augment "/interface:interface/interface:gigabitethernet/interface:ip" {
        uses interface-gi-dhcp;
    }
}
