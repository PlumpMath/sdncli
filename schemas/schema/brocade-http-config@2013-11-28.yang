/***********************************************************************
 * brocade-http-config.yang: Brocade HTTP Services data model
 *
 * Nov 2013, Vivek Padmanabhan
 *
 * Copyright (c) 2013-2014 by Brocade Communications Systems, Inc.
 * All rights reserved.
 *
 **********************************************************************/

module brocade-http-config {
    namespace "urn:brocade.com:mgmt:brocade-http";
    prefix "http-config";

    import tailf-common {
        prefix tailf;
    }

	import brocade-common-def {
        prefix common-def;
    }

    import brocade-rbridge {
        prefix rbridge;
    }

    organization
        "Brocade Communications Systems, Inc.";

        contact
        "Brocade Communications Systems, Inc.
         Postal: 130 Holger Way
                 San Jose, CA 95134
                  U.S.A
         Tel: +1-408-333-8000
         E-mail: support@Brocade.com
         web: www.brocade.com.";

        description
        "Instrument to configure HTTP Server";

        revision "2013-11-28" {
        description
            "Initial version of this module.";
        }

    grouping http-group {
	    container http {

    	    container server {

	            leaf shutdown {
	                type empty;
            	}
        	}
    	}
    }
	/* Define the "show http server status" functionality */
	augment "/common-def:show" {
        container http {
            container server {
                tailf:action status {
                    input {
                        leaf rbridge-id {
                            mandatory false;
                            type common-def:rbridge-id-all-type;
                        }
                    }
                    output {
                    }
                }
            }
        }
    }
    augment "/rbridge:rbridge-id" {
        uses http-group;
    }
    container http-sa { 
        uses http-group;
    }
}
