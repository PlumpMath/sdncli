/***********************************************************************
 * brocade-ip-forward.yang: Brocade IP Forwarding data model.
 *
 * Jul 2011, Sanjeev C Joshi
 *
 * Copyright (c) 2010 by Brocade Communications Systems, Inc.
 * All rights reserved.
 *
 **********************************************************************/
module brocade-ip-forward {
	namespace "urn:brocade.com:mgmt:brocade-ip-forward";
	prefix "ip-forward";

	import tailf-common { prefix "tailf"; }
	import ietf-inet-types  { prefix "inet"; }
	import brocade-common-def { prefix "common-def"; }
	import brocade-rbridge { prefix rbridge; }
	import brocade-vcs { prefix "vcs"; }

	organization
		"Brocade Communications Systems, Inc.";

	contact
		"Brocade Communications Systems, Inc.
		Postal: 1745 Technology Drive,
			San Jose, CA 95110
			U.S.A
		Tel: +1-408-392-6061
		E-mail: support@Brocade.com
		web: www.brocade.com.";

	description
		"This management module is an instrumentationfor the management
		of CIDR multipath IP Routes. Multipath IP routes have the
		same network  number but differing network masks.";

	revision "2011-07-18" {
		description
			"Initial version of this management module.";
	}

	grouping ipv6_route {
      container ipv6route {
		list route {
			//tailf:callpoint ipv6routestaticcpt;
			key "dest";
			leaf dest {
				type inet:ipv6-prefix;
			}

			choice next {
				mandatory true;
				case ipv6-hop {
					leaf next-hop {
						type inet:ipv6-address;
					}
				}
			}
		}
      }
	}

	augment "/rbridge:rbridge-id/rbridge:ipv6" {
		when '/vcs:vcsmode/vcs:vcs-mode = "true"';
		uses ipv6_route;
	}

	augment "/common-def:ipv6" {
		when '/vcs:vcsmode/vcs:vcs-mode = "false"';
		uses ipv6_route;
	}
}
