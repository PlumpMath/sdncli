/********************************************************************
 * brocade-interface-ext.yang:An Extension Model to Brocade Interface
 *                             Management Data Model
 *
 * July 2011, Mayank Maheshwari, Sanjeev C Joshi 
 *
 * Copyright (c) 2011, 2014 by Brocade Communications Systems, Inc.
 * All rights reserved.
 *
 ********************************************************************/
module brocade-interface-ext {
    namespace "urn:brocade.com:mgmt:brocade-interface-ext";
    prefix "interface-extensions";

    import tailf-common {
        prefix tailf;
    }

    import ietf-yang-types {
        prefix "yang";
    }

    import brocade-interface {
       prefix interface;
    }

	import brocade-common-def {
        prefix common-def;
    }

    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "This module is an extension to interface model for 
          - Defining RPCs to retrieve interface related operational data
            in the managed device.
          
        Glossary of the terms used:
        --------------------------- 
        HDLC - High-Level Data Link Control.
        PPP  - Point-to-Point Protocol.
        ATM  - Asynchronous Transfer Mode.
        GBIC - Gigabit Interface Converter.
        SFP  - small form-factor.
        XFP  - 10 Gigabit Small Form Factor Pluggable.
        xFF  -
        XFP-E - XFP Extended.
        ISL   - Inter switch Link.
        ";

    revision "2014-04-01" {
        description     
            "Added interface statistics related counters in the 
            output section of the 'get-interface-detail' rpc.";
    }
    
    revision "2011-07-05" {
        description     
            "Initial version of this management module.";
    }

    typedef line-speed {
        type enumeration {
            enum nil {
                value 1;
            }
            enum auto {
                value 2;
            }
            enum 1Gbps {
                value 3;
            }
            enum 10Gbps {
                value 4;
            }
            enum 40Gbps {
                value 5;
            }
            enum 100Mbps {
                value 6;
            }
            enum 2Gbps {
                value 7;
            }
            enum 4Gbps {
                value 8;
            }
            enum 8Gbps {
                value 9;
            }
            enum 16Gbps {
                value 10;
            }
            enum 100Gbps {
                value 11;
            }
        }
        units "Bits per Second";
    }

    grouping media-vendor-attr {
        leaf vendor-name {
            type string; 
            description 
                "This indicates the Vendor of this interface."; 
        }
        leaf vendor-oui {
            type string; 
            description 
                "This indicates the Vendor IEEE company ID."; 
        }
        leaf vendor-pn {
            type string;
            description 
                "This indicates the Part number."; 
        }
        leaf vendor-rev {
            type string;
            description 
                "This indicates the Revision level."; 
        }
    }

    grouping sfp-attr {
        leaf distance {
            type enumeration {
                enum short-dist {
                    value 1;
                }
                enum inter-dist {
                    value 2;
                }
                enum long-dist {
                    value 3;
                }
                enum unknown {
                    value 4;
                }
            }
        }
        leaf media-form-factor {
            type enumeration {
                enum sm {
                    value 1;
                }
                enum mx {
                    value 2;
                }
                enum m5 {
                    value 3;
                }
                enum m6 {
                    value 4;
                }
                enum tv {
                    value 5;
                }
                enum mi {
                    value 6;
                }
                enum tp {
                    value 7;
                }
                enum tw {
                    value 8;
                }
                enum unknown {
                    value 9;
                }
            }
        }
        leaf wavelength {
            type string;
            description 
                "Wavelength of pluggable media";
        }
        leaf serial-no {
            type string;
            description 
                "This indicates the Serial number.";
        }
        leaf date-code {
            type string;
            description 
                "This indicates the Vendor's 
                 manufactoring date code.";
        }
        leaf temperature {
            type uint32;
            mandatory false; 
            description 
                "This indicates the  Module
                 temperature (degrees C)";
        }
        leaf voltage {
            type decimal64 {
                fraction-digits 1;
            }
            mandatory false; 
            description 
                "This indicates the Supply voltage
                 (Volts)";
        }
        leaf current {
            type decimal64 {
                fraction-digits 3;
            }
            mandatory false; 
            description 
                "This indicates the Laser diode
                 drive current (milliAmps)";
        }
        leaf tx-power {
            type decimal64 {
                fraction-digits 1;
            }
            mandatory false; 
            description 
                "This indicates the Transmitted
                 optical power (microWatts)";
         }
         leaf rx-power {
             type decimal64 {
                 fraction-digits 1;
             }
             mandatory false; 
             description 
                 "This indicates the Received
                  optical power (microWatts)";
          }
    }

    grouping media-attr {
        leaf speed {
            type line-speed; 
            description 
                "The actual line speed of this interface.";
        }
        leaf connector {
            type enumeration {
                enum sc {
                    value 1;
                }
                enum style-1-copper {
                    value 2;
                }
                enum style-2-copper {
                    value 3;
                }
                enum bnc-tnc {
                    value 4;
                }
                enum coaxial {
                    value 5;
                }
                enum fiber-jack {
                    value 6;
                }
                enum lc {
                    value 7;
                }
                enum mt-rj {
                    value 8;
                }
                enum mu {
                    value 9;
                }
                enum sg {
                    value 10;
                }
                enum optical-pigtail {
                    value 11;
                }
                enum mpo-parallel-optic {
                    value 12;
                }
                enum mpo {
                    value 13;
                }
                enum hssdc-ii {
                    value 32;
                }
                enum copper-pigtail {
                    value 33;
                }
                enum cat-5-copper-cable {
                    value 34;
                }
                enum no-separable-connector {
                    value 36;
                }
                enum unknown {
                    value 35;
                }
            } 
            description 
                "This specifies the type of connector
                connected to the interface.";
        }
        leaf encoding {
            type enumeration {
                enum rz {
                    value 1;
                }
                enum nrz {
                    value 2;
                }
                enum sonet {
                    value 3;
                }
                enum 8b10b {
                    value 4;
                }
                enum 64b66b {
                    value 5;
                }
                enum 4b5b {
                    value 6;
                }
                enum manchester {
                    value 7;
                }
                enum ieee-802-3ab {
                    value 8;
                }
                enum sonet-scrambled {
                    value 9;
                }
                enum unknown {
                    value 10;
                }
            }
            description 
                "This indicates the type of encoding used to
                transmit the data on this interface."; 
        }
        uses media-vendor-attr;
    }

    rpc get-vlan-brief {
        description 
            "This is a function that returns operational data for a 
            given vlan and enumeration of all the interfaces belonging 
            to this vlan. The vlan output records are fetched similar
            to the snmp get-next model. When no input is given to this
            rpc, first set of vlan output records will be fetched. If
            there are any more extra vlan output records that are there
            to be fetched, the flag has-more at the end of the output
            will be set to true and the next set of vlan records will
            have to be fetched by querying with the last-vlan-id, in
            get-next-request, as the input to this function, again.
            When a vlan-id is  given as an input argument in the 
            get-request case, only that corresponding vlan output 
            record, if exists, will be fetched.";
            
        input {
            choice request-type {
                case get-request {
                    leaf vlan-id {
                        type interface:vlan-type;
                        description 
                            "This specifies vlan id for which this 
                             function is invoked. This is optional 
                             input, when not specified means 
                             'all' vlans.";
                    }
                }
                case get-next-request {
                    leaf last-rcvd-vlan-id {
                        type interface:vlan-type;
                        description 
                            "This specifies the vlan-id, from which
                             the next set of vlan output records are
                             to be fetched.";
                    }
                }
            }
        }

        output {
            leaf configured-vlans-count {
                type uint32;
                mandatory false; 
                description
                    "This indicates the total number of vlans configured.";
            }

            leaf provisioned-vlans-count {
                type uint32;
                mandatory false; 
                description
                    "This indicates the total number of vlans provisioned.";
            }

            leaf unprovisioned-vlans-count {
                type uint32;
                mandatory false; 
                description
                    "This indicates the total number of vlans unprovisioned.";
            }

            list vlan{
                key vlan-id;
                description 
                    "The list of vlans. Each row represents a vlan  and 
                    its operational characteristics in the managed 
                    device.";
                    
                leaf vlan-id {
                    type interface:vlan-type;
                    description 
                        "This indicates the Vlan identifier of this
                        vlan.";
                }

                leaf vlan-type {
                    type enumeration {
                        enum fcoe {
                            value 1;
                            description 
                                "FCOE vlan";
                        }
                        enum static {
                            value 2;
                            description 
                                "Static vlan";
                        }
                    }
                    description 
                        "This indicates the type of the vlan. 
                        The 'fcoe' value indicates that the vlan 
                        corresponding to it is an FCOE vlan.
                        The 'static' value indicates that the vlan 
                        corresponding to it is a Static vlan."; 
                }
                
                leaf vlan-name {
                    type string;
                    description 
                        "The indicates administrative name of this 
                        vlan.";
                }
                
                leaf vlan-state {
                    type enumeration {
                        enum invalid {
                            value 1;
                            description 
                                "The vlan is an invalid state";
                        }
                        enum suspend {
                            value 2;
                            description 
                                "The vlan is inactive as there are no member ports";
                        }
                        enum active {
                            value 3;
                            description 
                                "The vlan is in active state";
                        }
                        enum members-down {
                            value 4;
                            description 
                                "The vlan is inactive as members are down";
                        }
                    }
                    description 
                        "This indicates the operational state of this 
                        vlan.";
                }
                
                list interface {
                    key "interface-type interface-name";
                    uses interface:interface-name-info;
                    description
                        "This is a list of interfaces which form the 
                        membership for this vlan. Each row represents 
                        an interface (physical/logical) with relevant
                        operational details.";
                        
                    leaf tag {
                        type enumeration {
                            enum untagged {
                                value 1;
                                description 
                                    "This indicates that the interface
                                    is in access mode.";
                            }
                            enum tagged {
                                value 2;
                                description 
                                    "This indicates that the interface
                                    is in trunk mode.";
                            }
                            enum converged {
                                value 3;
                                description 
                                    "This indicates that the interface
                                    is in hybrid mode.";
                            }
                        }
                    }
                    list classification {
                        description
                            "This specifies the list of vlan classifications applied 
                            on a given vlan and an interface pair.";

                        key "classification-type classification-value";

                        leaf classification-type {
                        
                            description
                                "This specifies the type of classifications,
                                 which can be ctag, mac or vni.";
                            type enumeration {
                                enum none {
                                    value 0;
                                    description
                                        "unknown classification of vlan";
                                }
                                enum ctag {
                                    value 1;
                                    description
                                        "ctag based classification of vlan.";
                                }
                                enum mac {
                                    value 2;
                                    description
                                        "mac based classification of vlan.";
                                }
                                enum vni {
                                    value 3;
                                    description
                                        "vni based classification of vlan.";
                                }
                                enum mac-group {
                                    value 4;
                                    description
                                        "mac-group based classification of vlan.";
                                }
                            }
                        }
                        leaf classification-value {
                            type string;
                            description
                                "This specifies value of the vlan classification.";
                        }
                    }
                }
            }
            leaf last-vlan-id {
                type interface:vlan-type;
                description 
                    "This specifies the last vlan record that has been 
                     fetched.";
            }
            leaf has-more {
                type boolean;
                description
                    "This indicates whether there are more vlan
                     records to fetch or not.";
            }
        }
    }

    rpc get-interface-switchport {
        description 
            "This is a function that returns switch-port/L2 
            characteristics of all the interfaces in the managed 
            device.";

        output {
            list switchport {
                key "interface-type interface-name";
                uses interface:interface-name-info {
                    description
                        "Interface type and name.";
                }
                description 
                    "This is a list of all the switch-ports in the 
                    managed device. Each row represents an L2 port 
                    along with the operational characteristics.";
                    
                leaf mode {
                    type interface:switchport-mode-type;
                    description 
                        "This indicates the mode of Layer2 interface.";
                }
                
                leaf fcoe-port-enabled {
                    type boolean;
                    description 
                        "This indicates if the FCoE capability is 
                        enabled on this interface.
                        
                        The value of 'true' indicates that the port is 
                        enabled for FCoE. The value of 'false' 
                        indicates that the port is not enabled for 
                        FCoE.";
                }
                
                leaf ingress-filter-enabled {
                    type boolean;
                    description 
                        "This indicates if the 'Ingress filtering' is 
                        enabled for this interface.
                        
                        The value of 'true' indicates that the port is 
                        enabled for 'Ingress filtering'. The value of 
                        'false' indicates that the port is not enabled 
                        for 'Ingress filtering'.";
                }
                
                leaf acceptable-frame-type {
                    type enumeration {
                        enum admit-all {
                            value 1;
                            description 
                                "All frames are admitted.";
                        }
                        enum admit-only-vlan-tagged {
                            value 2;
                            description 
                                "Only tagged vlans are allowed.";
                        }
                    }
                    description 
                        "This specifies the switch-port ingress 
                        Frame admission policy - whether only tagged 
                        Frames are allowed or all.";
                }
                
                leaf default-vlan {
                    type interface:vlan-type;
                    description 
                        "This indicates the 'default vlan' identifier 
                        value for this switch-port. If switch-port mode 
                        as indicated by the value of the corresponding 
                        instance of 'mode' is 'trunk', Native vlan is 
                        returned. If switch-port mode is 'access', 
                        default vlan is returned.";
                }
                container active-vlans {
                    description 
                        "A conceptual group indicating the active vlans
                        for this switch-port interface.";
                    leaf-list vlanid {
                        type interface:vlan-type;
                        description
                            "This is a list of active vlan 
                            identifiers.";
                    }
                }
                container inactive-vlans {
                    description 
                        "A conceptual group indicating the in-active 
                        vlans for this switch-port interface.";
                    leaf-list vlanid {
                        type interface:vlan-type;
                        description
                            "This is a list in-active vlan 
                            identifiers.";
                    }
                }
            }
        }
    }

    rpc get-ip-interface {
        description
            "This is a function that serves to return brief details 
            of all interfaces, loopback and VE interface details of  
            particular managed entity. Phy interface details of 
            particular managed entity cannot be given";

        input {
            choice request-type {
                case get-request {
                    uses interface:interface-name-info {
                        description
                            "This specifies the interface for which
                            this function is  invoked. This is 
                             optional input, when not specified means
                            'all' interfaces in the managed entity.";
                    }

                    leaf rbridge-id {
                        mandatory false; 
                        type uint32 {
                            range "1..255" {
                            }
                       }
                   }
               }
            }  
        }
        
        output {
            list interface {
                key "interface-type interface-name";
                description 
                    "A list of interface entries. Each row represents
                    management information applicable to a particular
                    interface.";
                    
                uses interface:interface-name-info;
                           
                leaf if-name {
                    type string;
                    description
                        "This indicates the interface display name as 
                        in MIB-II's ifTable. However interface-name and
                        interface-type values of this instance forms 
                        fully qualified name for this interface.";
                }
                
                list ip-address {
                    key ipv4;
                    description
                        "This indicates whether IP address is primary/secondary
                        and corresponding Broadcast IP";

                    leaf ipv4 { 
                        type string;
                        description
                            "A.B.C.D/M IP address in dotted decimal/Mask";
                    }
                    
                    leaf ipv4-type {
                        mandatory false;
                        type enumeration {
                            enum primary {
                                value 1;
                                description
                                    "Primary IP address.";
                            }
                            enum secondary {
                                value 2;
                                description
                                    "Secondary IP address.";
                            }
                        }
                    }         		
                    
                    leaf broadcast {
                        mandatory false;
                        type string;
                        description
                            "Broadcast IP address.";
                    }

                    leaf ip-mtu {
                        mandatory false;
                        type interface:mtu-type;
                        units "Bytes";
                        description 
                            "This specifies the IP MTU value of this 
                            interface.";
                    }
               } 

                leaf if-state {
                    type enumeration {
                        enum unknown {
                            value 1;
                            description 
                                "status cannot be determined for some 
                                reason.";
                        }
                        enum up {
                            value 2;
                            description 
                                "ready to pass packets.";
                        }
                        enum down {
                            value 3;
                            description 
                                "down state.";
                        }
                        enum testing {
                            value 4;
                            description 
                                "in a test mode.";
                        }
                    }
                    description 
                        "This indicates the current operational state
                        of this interface. The 'testing' state 
                        indicates that no operational packets can be
                        passed. If 'shutdown' leaf of corresponding 
                        interface instance of brocade-interface module
                        is set, then 'if-state' should be 'down'. 
                        If 'shutdown' is changed deleted, then 
                        'if-state' should change to 'up' if the 
                        interface is ready to transmit and receive 
                        network traffic; it should remain in the 'down'
                        state if and only if there is a fault that 
                        prevents it from going to the 'up' state.";
                }


                leaf line-protocol-state {
                    type enumeration {
                        enum unknown {
                            value 1;
                            description 
                                "status cannot be determined for some
                                reason.";
                        }
                        enum up {
                            value 2;
                            description
                                "Line protocol state up.";
                        }
                        enum down {
                            value 3;
                            description 
                                "Line protocol state down.";
                        }
                    }
                    description 
                        "This indicates the 'Line protocol' state of
                        this interface.";
                }

                leaf proxy-arp {
                    mandatory false;
                    type string;
                    description
                        "This indicates the 'proxy-arp' state of the
                        interface.";
                }     

                leaf vrf {
                    mandatory false;
                    type string;   
                    description
                        "This indicates the 'vrf' of the interface.";
                }
            }

            leaf has-more {
                type boolean;
                    description
                        "Informs whether backend has more
                         interfaces that are not part of 
                         current response. Based on this
                         flag remaining interfaces can be 
                         fetched with another request";
            }
        }
    }

    rpc get-interface-detail {
        description 
            "This is a function that serves to return all the possible
            interfaces of the managed entity. This function can be used
            to discover basic characteristics of all the interfaces in
            the system. Each sub-layer below the internetwork-layer of
            a network interface is considered to be an interface.";
            
        reference 
            "K. McCloghrie, 'The Interfaces Group MIB', RFC 2863, 
            June 2000.";
            
        input {
        choice request-type {
            case get-request {
                uses interface:interface-name-info {
                        description
                            "This specifies the interface for which
                             this function is  invoked. This is 
                             optional input, when not specified means
                             'all' interfaces in the managed entity.";
                 }
            }
            case get-next-request {
                container last-rcvd-interface {
                        uses interface:interface-name-info{
                        description
                             "This specifies the last interface
                             received in the preceeding request.
                             Is an optional field for the first
                             request. For subsequent requests
                             this must be filled with the last 
                             interface received in the
                             preceding request.";
                        }
                    }
            }
        }
    }

        output {
            list interface {
                key "interface-type interface-name";
                description 
                    "A list of interface entries. Each row represents
                    management information applicable to a particular
                    interface.";
                    
                uses interface:interface-name-info;
                
                leaf ifindex {
                    type uint64;
                    description 
                        "A unique value, greater than zero, for each
                        interface.";
                }
                
                leaf mtu {
                    type interface:mtu-type;
                    default 2500;
                    units "Bytes";
                    description 
                        "The size of the largest packet which can be 
                        sent/received on the interface, specified in 
                        octets. For interfaces that are used for
                        transmitting network datagrams, this is the
                        size of the largest network datagram that can 
                        be sent on the interface.";
                }
                
                leaf ip-mtu {
                    type interface:mtu-type;
                    units "Bytes";
                    description 
                        "This specifies the IP MTU value of this 
                        interface.";
                }
                
                leaf if-name {
                    type string;
                    description
                        "This indicates the interface display name as 
                        in MIB-II's ifTable. However interface-name and
                        interface-type values of this instance forms 
                        fully qualified name for this interface.";
                }
                
                leaf if-state {
                    type enumeration {
                        enum unknown {
                            value 1;
                            description 
                                "status cannot be determined for some 
                                reason.";
                        }
                        enum up {
                            value 2;
                            description 
                                "ready to pass packets.";
                        }
                        enum down {
                            value 3;
                            description 
                                "down state.";
                        }
                        enum testing {
                            value 4;
                            description 
                                "in a test mode.";
                        }
                    }
                    description 
                        "This indicates the current operational state
                        of this interface. The 'testing' state 
                        indicates that no operational packets can be
                        passed. If 'shutdown' leaf of corresponding 
                        interface instance of brocade-interface module
                        is set, then 'if-state' should be 'down'. 
                        If 'shutdown' is changed deleted, then 
                        'if-state' should change to 'up' if the 
                        interface is ready to transmit and receive 
                        network traffic; it should remain in the 'down'
                        state if and only if there is a fault that 
                        prevents it from going to the 'up' state.";
                }
                
                leaf line-protocol-state {
                    type enumeration {
                        enum unknown {
                            value 1;
                            description 
                                "status cannot be determined for some
                                reason.";
                        }
                        enum up {
                            value 2;
                            description
                                "Line protocol state up.";
                        }
                        enum down {
                            value 3;
                            description 
                                "Line protocol state down.";
                        }
                    }
                    description 
                        "This indicates the 'Line protocol' state of
                        this interface.";
                }
                
                leaf line-protocol-state-info {
                    type string;
                    description 
                        "This indicates the reason for the current line
                        protocol state of this interface.";
                }
                
                leaf line-protocol-exception-info {
                    type string;
                    description 
                        "This indicates the 'Exception information' of 
                        line protocol.";
                }
                
                leaf hardware-type {
                    type enumeration {
                        enum unknown {
                            value 1;
                            description 
                                "none of the other enumerations 
                                defined.";
                        }
                        enum ethernet {
                            value 2;
                            description
                                "for all ethernet-like interfaces,
                                regardless of speed, as per RFC3635.";

                        }
                        enum loopback {
                            value 3;
                            description
                                "loop back address.";
                        }
                        enum hdlc {
                            value 4;
                            description
                                "HDLC interface.";
                        }
                        enum ppp {
                            value 5;
                            description 
                                "PPP interface.";
                        }
                        enum atm {
                            value 6;
                            description
                                "ATM interface.";
                        }
                        enum vlan {
                            value 7;
                            description 
                                "Layer 2 Virtual LAN using 802.1Q.";
                        }
                        enum aggregate {
                            value 8;
                            description
                                "IEEE 802.3ad Link Aggregate.";
                        }
                        enum frame-relay {
                            value 9;
                            description 
                                "Frame-relay.";
                        }
                        enum tunnel {
                            value 10;
                            description
                                "tunnel/encapsulation.";
                        }
                    }
                    description 
                        "This indicates the type of this interface.";
                }
                
                leaf logical-hardware-address {
                    type yang:mac-address;
                    description 
                        "This indicates the address of this interface at
                        its protocol sub-layer.";
                }
                
                leaf current-hardware-address {
                    type yang:mac-address;
                    description 
                        "This indicates the address of this interface at
                        its protocol sub-layer.";
                }
                
                leaf media-type {
                    type enumeration {
                        enum unknown {
                            value 1;
                            description 
                                "none of the other enumerations 
                                defined.";
                        }
                        enum gbic {
                            value 2;
                            description 
                                "GBIC.";
                        }
                        enum fixed {
                            value 3;
                            description 
                                "Fixed.";
                        }
                        enum sfp {
                            value 4;
                            description
                                "SFP based.";
                        }
                        enum xfp {
                            value 5;
                            description
                                "XFP.";
                        }
                        enum xff {
                            value 6;
                            description
                                "XFF.";
                        }
                        enum xfp-e {
                            value 7;
                            description
                                "XFP-E.";
                        }
                        enum qsfp {
                            value 12;
                            description
                                "QSFP.";
                        }
                        enum qsfpp {
                            value 13;
                            description
                                "QSFPP.";
                        }
                        enum cfp {
                            value 14;
                            description
                                "CFP.";
                        }
                        enum cfp2 {
                            value 17;
                            description
                                "CFP2.";
                        }
                    }
                    description 
                        "The specifies the type of the media plugged in
                        for this interface.";
                }
                
                leaf wavelength {
                    type uint32;
                    description 
                        "Wavelength of pluggable media";
                }
                
                leaf if-description {
                    type string;
                    description 
                        "This specifies a textual string containing
                        information about the interface.";
                }
                
                leaf actual-line-speed {
                    type string;
                    description 
                        "The actual line speed of this interface.";
                }
                
                leaf configured-line-speed {
                    type line-speed;
                    description 
                        "The administratively configured line speed of
                        this interface. This should be same as what is
                        returned by value of corresponding instance of
                        'speed' of 'brocade-interface' module.";
                }
                
                leaf line-duplex-state {
                    type enumeration {
                        enum unknown {
                            value 1;
                            description
                                "The state cannot be determined for
                                some reason.";
                        }
                        enum half {
                            value 2;
                            description 
                                "half-duplex mode.";
                        }
                        enum full {
                            value 3;
                            description
                                "full-duplex mode.";
                        }
                    }
                    description 
                        "This indicates the 'Line duplex state' of this
                        interface.";
                }
                
                leaf flow-control {
                    type bits {
                        bit received {
                            position 0;
                        }
                        bit transmitted {
                            position 1;
                        }
                    }
                    description 
                        "This indicates the 'Flow control' for this
                        interface.";
                }
                
                leaf queuing-strategy {
                    type enumeration {
                        enum fifo {
                            value 1;
                            description 
                                "FIFO.";
                        }
                    }
                    description 
                        "This indicates the 'Queuing strategy' for 
                        this interface.";
                }
                
                leaf port-role {
                    type enumeration {
                        enum isl {
                            value 1;
                            description 
                                "ISL port.";
                        }
                        enum edge {
                            value 2;
                            description 
                                "Edge port.";
                        }
                    }
                    description 
                        "This indicates current that this interface is
                        playing. This is applicable only for physical
                        interfaces.";
                }
                
                leaf port-mode {
                    type enumeration {
                        enum unknown {
                            value 0;
                            description 
                                "Port mode is unknown";
                        }
                        enum l3 {
                            value 1;
                            description 
                                "Layer3.";
                        }

                        enum l2 {
                            value 2;
                            description 
                                "Layer2.";
                        }
                        enum mirror {
                            value 3;
                            description
                                "Port mode is 'mirror'.  Mirrored port
                                can't be configured with L3/L2 
                                configurations.";
                        }

                    }
                    description
                        "This indicates operational mode of this 
                        interface. This is applicable only for physical
                        interfaces/port channel interfaces.";
                }

                leaf ifHCInOctets {
                    type yang:counter64;
                    description   
                        "The total number of octets received on the 
                        interface, including framing characters.";
                }
 
                leaf ifHCInUcastPkts {
                    type yang:counter64;
                    description   
                        "The number of packets, delivered by this 
                        sub-layer to a higher (sub-)layer, which were 
                        not addressed to a multicast or broadcast 
                        address at this sub-layer.";
                }

                leaf ifHCInMulticastPkts {
                    type yang:counter64;
                    description   
                        "The number of packets, delivered by this 
                        sub-layer to a higher (sub-)layer, which were 
                        addressed to a multicast address at this 
                        sub-layer. For a MAC layer protocol, this
                        includes both Group and Functional addresses.";
                }

                leaf ifHCInBroadcastPkts {
                    type yang:counter64;
                    description   
                        "The number of packets, delivered by this 
                        sub-layer to a higher (sub-)layer, which were 
                        addressed to a broadcast address at this 
                        sub-layer.";
                }

                leaf ifHCInErrors {
                    type  yang:counter64;
                    description 
                        "For packet-oriented interfaces, the number of 
                        inbound packets that contained errors 
                        preventing them from being deliverable to a 
                        higher-layer protocol. For character-oriented 
                        or fixed-length interfaces, the number of 
                        inbound transmission units that contained 
                        errors preventing them from being deliverable 
                        to a higher-layer protocol.";
                }            

                leaf ifHCOutOctets {
                    type yang:counter64;
                    description   
                        "The total number of octets transmitted out of 
                        the interface, including framing characters.";
                }

                leaf ifHCOutUcastPkts {
                    type yang:counter64;
                    description   
                        "The total number of packets that higher-level 
                        protocols requested be transmitted, and which 
                        were not addressed to a multicast or broadcast 
                        address at this sub-layer, including those 
                        that were discarded or not sent.";
                }

                leaf ifHCOutMulticastPkts {
                    type yang:counter64;
                    description   
                        "The total number of packets that higher-level 
                        protocols requested be transmitted, and which 
                        were addressed to a multicast address at this 
                        sub-layer, including those that were discarded 
                        or not sent.  For a MAC layer protocol, this
                        includes both Group and Functional addresses.";
                }

                leaf ifHCOutBroadcastPkts {
                    type yang:counter64;
                    description   
                        "The total number of packets that higher-level 
                        protocols requested be transmitted, and which 
                        were addressed to a broadcast address at this 
                        sub-layer, including those that were discarded 
                        or not sent.";
                }

                leaf ifHCOutErrors {
                    type yang:counter64;
                    description 
                        "For packet-oriented interfaces, the number of 
                        outbound packets that could not be transmitted 
                        because of errors. For character-oriented or 
                        fixed-length interfaces, the number of 
                        outbound transmission units that could not be 
                        transmitted because of errors.";
                }
            }
            leaf has-more {
                type boolean;
                description
                    "Informs whether backend has more
                    interfaces that are not part of 
                    current response. Based on this
                    flag remaining interfaces can be 
                    fetched with another request.";
            }            
        }
    }

    rpc get-media-detail {
        description 
            "This is a function that serves to return the media 
            properities of all the interfaces of the managed entity.";
        input {
            uses interface:interface-name-info {
                description 
                    "This specifies the interface for which this 
                    function is  invoked. This is optional input, 
                    when not specified means 'all' interfaces in the 
                    managed entity.";
            }

            leaf rbridge-id {
                mandatory false; 
                type common-def:rbridge-id-type;
                description
                    "This specifies the unique identifier for the switch";
            }
        }
        output {
            list interface {
                key "interface-type interface-name";
                description 
                    "A list of interface entries. Each row represents
                    management information applicable to a particular 
                    interface.";
                uses interface:interface-name-info;
                choice interface-identifier {
                    case sfp {
                        container sfp { 
                            uses media-attr;
                            uses sfp-attr;
                        }
                    }
                    case on-board {
                        container on-board {
                            uses media-attr;
                        }
                    }
                    case gbic {
                        container gbc {
                            uses media-vendor-attr;
                        }
                    }
                    case xfp {
                        container xfp {
                            uses media-vendor-attr;
                        }
                    }
                    case xff {
                        container xff {
                            uses media-vendor-attr;
                        }
                    }
                    case xfpe {
                        container xfpe {
                            uses media-vendor-attr;
                        }
                    }
                    case unknown {
                        container unknown {
                            uses media-vendor-attr;
                        }
                    }
                    case qsfp {
                        container qsfp {
                            uses media-attr;
                            uses sfp-attr;
                        }
                    }
                    case qsfpp {
                        container qsfpp {
                            uses media-attr;
                            uses sfp-attr;
                        }
                    }
                    case cfp {
                        container cfp {
                            uses media-attr;
                            uses sfp-attr;
                        }
                    }
                    case cfp2 {
                        container cfp2 {
                            uses media-attr;
                            uses sfp-attr;
                        }
                    }
                }
            }
        }
    }
}
