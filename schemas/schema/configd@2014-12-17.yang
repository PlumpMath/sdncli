module configd {
	namespace "urn:vyatta.com:mgmt:configd";
	prefix configd;

	organization "Brocade Communications Systems, Inc.";
	contact
		"Brocade Communications Systems, Inc.
		 Postal: 130 Holger Way
		 	 San Jose, CA 95134
		 E-mail: support@Brocade.com
		 Web: www.brocade.com";

	revision 2014-12-17 {
		description "Add rpc-script extension";
	}
	revision 2014-10-28 {
		description "Update for 3.2.1R1";
	}

	revision 2014-05-30 {
		description "Initial revision.";
	}

	extension help {
		argument text;
	}
	extension comp_help {
		argument text;
	}
	extension pattern-help {
		argument text;
	}

	extension priority {
		argument priority;
	}

	extension allowed {
		argument executable;
	}
	extension begin {
		argument executable;
	}
	extension end {
		argument executable;
	}
	extension create {
		argument executable;
	}
	extension delete {
		argument executable;
	}
	extension update {
		argument executable;
	}
	extension subst {
		argument executable;
	}
	extension secret {
		argument bool;
	}

	extension validate {
		argument executable;
	}
	extension syntax {
		argument executable;
	}
	
	extension error-message {
		argument message;
	}

	extension migration {
		argument level;
	}

	extension rpc-script {
		argument executable;
	}
}
