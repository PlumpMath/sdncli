/***********************************************************************
 * zone.yang-: Brocade Zone Data Model
 *
 * April 2011, Daniel Chung  
 *
 * Copyright (c) 2011 by Brocade Communications Systems, Inc.
 * All rights reserved.
 *
 **********************************************************************/
module brocade-zone {
    namespace "urn:brocade.com:mgmt:brocade-zone";
    prefix "brocade-zone";

    import tailf-common {
        prefix tailf;
    }
    
    import brocade-common-def {
        prefix common-def;
    }
    revision 2010-12-01 {
        description
            "Initial release.

             Contains Zone display & configuration implementations";
    }

    typedef cfg-action-type {
        type enumeration {
            enum cfg-none { 
                value 0;
            }

            enum cfg-save {
                value 1;
            }

            enum cfg-disable {
                value 2;
            }

            enum cfg-clear {
                value 3;
            }

            enum cfg-transaction-abort {
                value 4;
            }
        }
    }

    typedef default-zone-access-type {
        type enumeration {
            enum noaccess {
                value 0;
            }
            enum allaccess {
                value 1;
            }
        }
    }

    typedef cfg-memberzone-zonename-type {
        type string {
	    pattern '([0-9a-zA-Z_]{1,64})'
	        + '(;([0-9a-zA-Z_]{1,64}))*' {

	        description
		    "Cfg Member-zones can only consist of
		    alphanumeric strings of max length of
		    64 characters.  WWNs are not valid
		    cfg members.  The pattern checking
		    verifies that the string consists or
		    alphanumeric characters and underline
		    characters only.";
	    }
	}
	description
	    "Use the member-zone command to add one
	    or more members to a cfg. Users
	    can specify multiple entries in a single
	    command by separating members with a
	    semi-colon. However when using
	    the [no] option, only one member-zone
	    can be removed at a time.";
    }

    typedef zone-memberentry-entryname-type {
        type string {
	    pattern '(([0-9a-zA-Z_]{1,64})|'
	        + '([0-9a-fA-F]{2}(:[0-9a-fA-F]{2}){7}))'
	        + '(;(([0-9a-zA-Z_]{1,64})|([0-9a-fA-F]{2}'
	        + '(:[0-9a-fA-F]{2}){7})))*' {

	        description
		    "Zone Member-entries can consist of
		    WWNs and alphanumeric Alias strings
		    of max length 64 characters. The
		    pattern checking verifies that WWNs
		    are of valid syntax and that the
		    strings consists or alphanumeric
		    characters and underline characters
		    only.";
	    }
	}

	description
	    "Use the member-entry command to add one
	    or more members to a zone. Member
	    entries can consist of WWNs and/or
	    Alias-Names. Users can specify multiple
	    entries in a single command by
	    separating members with a semi-colon.
	    However when using the [no] option to
	    remove zone members, only one member-
	    entry can be removed at a time.";
    }

    typedef alias-memberentry-entryname-type {
        type string {
	    pattern '([0-9a-fA-F]{2}(:[0-9a-fA-F]'
	        + '{2}){7})(;[0-9a-fA-F]{2}(:[0-9a-fA-F]'
	        + '{2}){7})*' {

	        description
        	    "Alias Member-entries can consist of
		    WWNs only. The pattern checking
		    verifies that WWNs are of valid
		    syntax.";
	    }
	}
	description
	    "Use the member-entry command to add one
	    or more WWN members to an alias. Users
	    can specify multiple entries in a single
	    command by separating members with a
	    semi-colon. However when using the [no]
	    option to remove alias members, only
	    one member-entry can be removed at a
	    time.";
    }

    container zoning {
        container defined-configuration {
            list cfg {
                key "cfg-name";

                leaf cfg-name {
                    type string {
			length "1..64";
			pattern '[0-9a-zA-Z_]{1,64}' {

			description
        			"Cfgs can consist of alphanumeric
				and underline characters of max length
				of 64 characters. The pattern checking
				verifies that the specified name
				consists or alphanumeric
				characters and underline characters
				only.";
			}
		    }
                }

                list member-zone {
		    /* cli-suppress-list-no forces user to specify a
		     * cfg member to remove, otherwise command will
		     * be incomplete */
		    key "zone-name";
		       
		    leaf zone-name {
		        type string {
			    pattern '([0-9a-zA-Z_]{1,64})'
			        + '(;([0-9a-zA-Z_]{1,64}))*' {
			    
			        description
			       "Cfg Member-zones can only consist of
			       alphanumeric strings of max length of
			       64 characters.  WWNs are not valid
			       cfg members.  The pattern checking
			       verifies that the string consists or
			       alphanumeric characters and underline
			       characters only.";
			    }
			}

			description
			    "Use the member-zone command to add one
			    or more members to a cfg. Users
			    can specify multiple entries in a single
			    command by separating members with a
			    semi-colon. However when using
			    the [no] option, only one member-zone
			    can be removed at a time.";
		    }
                }
            }

            list zone {
                key "zone-name";

                leaf zone-name {
                    type string {
			length "1..64";
			pattern '[0-9a-zA-Z_]{1,64}' {

			description
        		    "Zones can consist of alphanumeric
			    and underline characters of max length
			    of 64 characters. The pattern checking
			    verifies that the specified name
			    consists or alphanumeric
			    characters and underline characters
			    only.";
			}
		    }
                }

                list member-entry {
		    /* cli-suppress-list-no forces user to specify a
		     * zone member to remove, otherwise command will
		     * be incomplete */
		    key "entry-name";
		       
		    leaf entry-name {
		        type string {
		    	pattern '(([0-9a-zA-Z_]{1,64})|'
		            + '([0-9a-fA-F]{2}(:[0-9a-fA-F]{2}){7}))'
		            + '(;(([0-9a-zA-Z_]{1,64})|([0-9a-fA-F]{2}'
		            + '(:[0-9a-fA-F]{2}){7})))*' {
		       
				description
				     "Zone Member-entries can consist of
				     WWNs and alphanumeric Alias strings
				     of max length 64 characters. The
				     pattern checking verifies that WWNs
				     are of valid syntax and that the
				     strings consists or alphanumeric
				     characters and underline characters
				     only.";
			    }
		        }
		       
		        description
			    "Use the member-entry command to add one
			    or more members to a zone. Member
			    entries can consist of WWNs and/or
			    Alias-Names. Users can specify multiple
			    entries in a single command by
			    separating members with a semi-colon.
			    However when using the [no] option to
			    remove zone members, only one member-
			    entry can be removed at a time.";
		    }
                }
            }

	    list alias {
                key "alias-name";

                leaf alias-name {
                    type string {
			length "1..64";
			pattern '[0-9a-zA-Z_]{1,64}' {

			description
        		    "Aliases can consist of alphanumeric
			    and underline characters of max length
			    of 64 characters. The pattern checking
			    verifies that the specified name
			    consists or alphanumeric
			    characters and underline characters
			    only.";
			}
		    }
                }

                list member-entry {
		    /* cli-suppress-list-no forces user to specify an
		     * alias member to remove, otherwise command will
		     * be incomplete */
		    key "alias-entry-name";
		    
		    leaf alias-entry-name {
		        type string {
		            pattern '([0-9a-fA-F]{2}(:[0-9a-fA-F]'
		            + '{2}){7})(;[0-9a-fA-F]{2}(:[0-9a-fA-F]'
		            + '{2}){7})*' {
		    
		            description
		    	    "Alias Member-entries can consist of
		    	    WWNs only. The pattern checking
		    	    verifies that WWNs are of valid
		    	    syntax.";
		            }
		        }

		    description
		    	"Use the member-entry command to add one
		    	or more WWN members to an alias. Users
		    	can specify multiple entries in a single
		    	command by separating members with a
		    	semi-colon. However when using the [no]
		    	option to remove alias members, only
		    	one member-entry can be removed at a
		    	time.";
		    }
                }
            }
        }

        container enabled-configuration {
    
            leaf cfg-name {
                type string;
            }

            leaf default-zone-access {
                type default-zone-access-type;
            }

            leaf cfg-action {
                type cfg-action-type;
            }
        }
    }  // end of zone container

    augment "/common-def:show" {
        container zoning {
            tailf:action operation-info {
                input {
                }
                output {
                    leaf db-max {
                        type uint32;
                    }

                    leaf db-avail {
                        type uint32;
                    }

                    leaf db-committed {
                        type uint32;
                    }

                    leaf db-transaction {
                        type uint32;
                    }

                    leaf transaction-token {
                        type uint32;
                    }

                    leaf last-zone-changed-timestamp {
                        type string;
                    }

                    leaf last-zone-committed-timestamp {
                        type string;
                    }
                }
            }

	    /* NOTE: 'zone show enabled-configuration' NOSCLI logic resides in /confd/cli/zone.cli */
        }
    }

    /*** RPC for 'zone show enabled-configuration' ***/
    rpc show-zoning-enabled-configuration {
         description
             "This will display the Zoning Enabled-Configuration
             database.";
         
	 input {
            choice request-type {
                case get-request {
                    leaf zone-name-pattern {
			mandatory false;
			type string;
                        description
                            "This specifies the enabled-zone for which
                             this function is invoked. This is 
                             optional input, when not specified means
                             to get the entire enabled-zone database.";
                    }
                }
                case get-next-request {
                    leaf last-rcvd-zone-name {
			mandatory false;
		        type string;
                        description
                           "This specifies the last enabled-zone
                            received in the preceeding request.
                            Is an optional field for the first
                            request. For subsequent requests
                            this must be filled with the last 
                            enabled-zone received in the
                            preceeding request.";
                    }
               }
	    }
	 }

         output {
             container enabled-configuration {
		leaf cfg-name {
		    type string;
		}

		list enabled-zone {
		    key "zone-name";
	
		    leaf zone-name {
		        type string;
		    }
	
		    list member-entry {
		        key "entry-name";
	
		        leaf entry-name {
			    type string;
		        }
		    }
		}

		leaf has-more {
                     type boolean;
                     description
                        "Informs whether backend has more
                        zoning output that is not part of 
                        the current response. Based on this
                        flag remaining enabled-zones can be 
                        fetched with another request";
		}
	     }
	 }
    }
}
