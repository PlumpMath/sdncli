/**************************************************************************
 * brocade-mac-address-table.yang: Brocade mac-address-table data model
 *
 * Feb 2011, 
 *
 * Copyright (c) 2011 by Brocade Communications Systems, Inc.
 * All rights reserved
 *
 **************************************************************************/

module brocade-mac-address-table {

    namespace "urn:brocade.com:mgmt:brocade-mac-address-table";
    prefix "mac-address-table";
	

    import tailf-common {
        prefix tailf;
    }

    import ietf-yang-types {
        prefix yang;
    }

    import brocade-interface {
        prefix interface;
    }

    import brocade-mac-access-list {
        prefix mac-access-list;
    }

    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "Mac forwarding table";

    revision "2011-02-15" {
        description
            "Added rpc to show mac-address-table for a given
            mac-address.";
    }

    typedef mac-address-table-aging-time {
        type uint32 {
            range "0|60..100000" {
            }
        }
        default 300;
    }

    typedef mac-address-table-interface {
      type enumeration {
        enum gigabitethernet {
          value 1;
        }
        enum tengigabitethernet {
          value 2;
        }
        enum fortygigabitethernet {
          value 3;
        }
        enum port-channel {
          value 4;
        }
        enum hundredgigabitethernet {
          value 5;
        }
      }
    }

    typedef mac-address-table-vlan {
      type enumeration {
        enum vlan { 
          value 1;
        }
      }
    }

    container mac-address-table {
		list static {

            key "mac-address forward interface-type interface-name vlan vlanid";
            leaf mac-address {
                type mac-access-list:mac-address-type;
            }

            leaf forward {
                type enumeration {
                    enum forward{
                        value 1;
                    }
                }
            }


            leaf interface-type {
                type enumeration {
                  	enum gigabitethernet {
                  	value 1;
                	}
                	enum tengigabitethernet {
                	value 2;
                	}
                	enum fortygigabitethernet {
                	value 3;
               	 	}
                	enum port-channel {
                	value 4;
                	}
                	enum hundredgigabitethernet {
                	value 5;
                	}
                }
            }

            leaf interface-name {
                type string;
            }


            leaf vlan {
                type enumeration {
                    enum vlan { 
		        value 1;
                    }
                }
            }

            leaf vlanid {
                type interface:vlan-type;
            }
		}		

        leaf learning-mode {
            description "Conversational Learning Mode";
            type enumeration {
                enum conversational {
                    value 1;
                }
            }
        }

        container aging-time {
            description "Aging Time";

            leaf conversational-time-out {
                type uint32 {
                    range "0|60..100000" {
                    }
                }
                default 300;
            }

            leaf legacy-time-out {
                type uint32 {
                    range "0|10..100000" {
                    }
                }
                default 300;
            }
        }

		container mac-move {
			description "MAC move";

			leaf mac-move-detect-enable {
               	description "Enable MAC move detect";
				type empty;
			}

			leaf mac-move-limit {
                description "MAC move detect limit (default = 20)";
				type uint32 {
                    range "5..500" {
                    }
                }
                default 20;
			}
		}

		container consistency-check {
			description "MAC Consistency check";

			leaf mac-consistency-check-suppress {
               	description "Suppress MAC Consistency check";
				type empty;
			}

			leaf mac-consistency-check-interval {
                description "MAC Consistency check interval in seconds (default = 300)";
				type uint32 {
                    range "120..3600" {
                    }
                }
                default 300;
			}
		}
    }

    /* mac-group specifies a group of mac addresses
    along with the mac address mask. */
    list mac-group {
        key mac-group-id;


        leaf mac-group-id {
            type interface:mac-group-id-type;
        }

        list mac-group-entry {
            key entry-address;
            leaf entry-address {
                type interface:mac-address-type;
            }
        }
    }

    rpc get-mac-address-table {

        description
            "This is a function that returns operational data for a
             given mac entry and the corresponding details of that mac
             entry. The mac entries are fetched similar to the snmp 
             get-next model. When no input is given to this rpc, first
             set of mac entries will be fetched. If there are any
             more extra mac entries that are there to be fetched,
             the flag has-more at the end of the o/p will be set to
             true. To get the next set of mac entries, this rpc has to
             be queried again with the last mac entry details of the
             previous set as the input in get-next-request case. With
             get-next-request all three fields i.e. last-mac-address,
             last-vlan-id and last-mac-type need to be passed as input.
			 When the rpc is queried with a mac-address as input in the 
             get-request case the corresponding mac entry, if exists,
             will be fetched.";

        input {
            choice request-type {
                case get-request {
                    leaf mac-address {
                        type yang:mac-address;
                        description
                            "The Mac Address for which the
                             corresponding mac entry will be
                             fetched. The i/p should be in 
                             xx:xx:xx:xx:xx:xx format.";
                    }
                }
                case get-next-request {
                    container last-mac-address-details {
                        leaf last-mac-address {
                            type yang:mac-address;
                            description
                                "The Mac Address information of the
                                 last mac entry in the previous set, 
                                 from which the next set of mac entries
                                 will be fetched. The i/p should be in 
                                 xx:xx:xx:xx:xx:xx format.";
                        }
                        leaf last-vlan-id {
                            type interface:vlan-type;
                            description
                                "The Vlan Id information of the
                                 last mac entry in the previous set, 
                                 from which the next set of mac entries
                                 will be fetched.";
                        }
                        leaf last-mac-type {
                            type enumeration {
                                enum static {
                                    value 1;
                                }
                                enum dynamic {
                                    value 2;
                                }
                                enum fpma {
                                    value 3;
                                }
                                enum system {
                                    value 4;
                                }
                            }
                            description
                                "The indicates whether the last mac entry
                                 in the previous set of entries is a
                                 static or a dynamic entry";
                        }
                    }
                }
            }
        }

        output {
            list mac-address-table {
                key "vlanid mac-address";
                leaf vlanid {
                    type interface:vlan-type;
                    description "vlan id";
                }
                leaf mac-address {
                    type yang:mac-address;
                    description "Mac Address";
                }
                leaf mac-type {
                    type enumeration {
                        enum static {
                            value 1;
                        }
                        enum dynamic {
                            value 2;
                        }
                        enum fpma {
                            value 3;
                        }
                        enum system {
                            value 4;
                        }
                    }
                    description "Mac Address type";
                }
                leaf mac-state {
                    type enumeration {
                        enum active {
                            value 1;
                        }
                        enum inactive {
                            value 2;
                        }
                        enum remote {
                            value 3;
                        }
                        enum unknown {
                            value 4;
                        }
                    }
                    description "Mac Address state";
                }
                list forwarding-interface {
                    description
                        "List of forwarding interfaces";
                    uses interface:interface-name-info;
                }
            }
            leaf has-more {
                type boolean;
                description
                    "This indicates whether there are more mac
                     records to fetch or not.";
            }
        }
    }
}
