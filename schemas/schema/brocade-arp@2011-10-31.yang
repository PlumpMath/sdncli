/***********************************************************************
 * brocade-arp.yang: Brocade ARP data model
 *
 * Jan 2011, jay pangalur , vamshi karnati
 *
 * Copyright (c) 2010 by Brocade Communications Systems, Inc.
 * All rights reserved.
 *
 **********************************************************************/
module brocade-arp {
    namespace "urn:brocade.com:mgmt:brocade-arp";
    prefix arp;
    
	import brocade-mac-access-list { prefix mac-access-list; }
    import brocade-interface { prefix interface; }
	import brocade-rbridge { prefix rbridge; }
    import brocade-vrf { prefix vrf; }
	import ietf-inet-types  { prefix "inet"; }
	import tailf-common { prefix tailf; }

	organization
		"Brocade Communications Systems, Inc.";

	contact
		"Brocade Communications Systems, Inc.
		Postal: 130 Holger way,
		San Jose, CA 95134,
		U.S.A
			Tel: +1-408-333-8000
			E-mail: support@Brocade.com
			web: www.brocade.com.";

	description
		"This management module is an instrumentation to manage
		ARPD Daemon";

    revision "2011-10-31" {
        description     
            "Initial version of this management module.";
    }         

	typedef slot-id {
		type uint8 {
			range 1..16 {
				description
					"Slot-ID;;  1..16";
			} // range
		} //type	
	} // slot-id

	grouping arp_cmds {
		container system-max {
            status obsolete;
			leaf arp {
				type uint32 {
					range "0..16384" {
					} // range
				}
				default 4096;
			} //arp

			description
				"Configure system-wide maximum values (reload required)'.
                This support is obsoleted.";
		} // system-max
        uses arp-entry-group;
    }


    grouping arp-entry-group {
		list arp-entry {
			key "arp-ip-address";

			leaf arp-ip-address {
				type inet:ipv4-address;
				description
					"IPv4 Address";
			} // ip-address

			leaf mac-address-value {
				type mac-access-list:mac-address-type;
			} // mac-address value

			leaf interfacename {
				type enumeration {
					enum interface {
						description
							"Interface to use";
							
					} // enum interface		
				}	//  type enumeration	
			} // interface name	
				
			choice interfacetype {
				/*case Port-channel {
					leaf Port-channel {
						description
							"Port-channel";
						type interface:portchannel-type;
					} // leaf Port-channel
				} // Port-channel */ /* Will be supported if there is a design change later */
				case GigabitEthernet {
					leaf GigabitEthernet {
						description
							"GigabitEthernet";
					type interface:interface-type;
					} // leaf GigabitEthernet
				}	// case GigabitEthernet

				case TenGigabitEthernet {
					leaf TenGigabitEthernet {
						description
							"TenGigabitEthernet";
					type interface:interface-type;
					} // leaf TenGigabitEthernet
				}	// case TenGigabitEthernet
				case FortyGigabitEthernet {
					leaf FortyGigabitEthernet {

						description
							"FortyGigabitEthernet";
					type interface:interface-type;
					} // leaf FortyGigabitEthernet
				}	// case FortyGigabitEthernet
                case HundredGigabitEthernet {
                    leaf HundredGigabitEthernet {

                        description
                            "HundredGigabitEthernet";
                    type interface:interface-type;
                    } // leaf HundredGigabitEthernet
                }   // case HundredGigabitEthernet

				case Ve {
					leaf Ve {
						description
							"Ve";
						type interface:vlan-type;
					} // leaf Vlan	
				} // case Vlan	
			} // interfacetype
		} // list arp-entry
	} // arp-entry-group
	
	augment "/rbridge:rbridge-id" {
		uses arp_cmds;
	}
		
	container hide-arp-holder {
		uses arp_cmds;
	}

    augment "/rbridge:rbridge-id/vrf:vrf/vrf:address-family/vrf:ip/vrf:unicast" {
        uses arp-entry-group;
    }

    rpc get-arp {
        description
            "This RPC returns ARP entries of the managed entity.
             Depending on the input argument, the ARP entries are
             displayed. When there is no input argument entered, all
             the ARP entries of the managed entity are returned.";
        input {
            choice input-type {
                case interface {
                    uses interface:interface-name-info;
                }
                case dynamic {
                    leaf dynamic {
                        type empty;
                        description
                            "This input queries for all the dynamic
                             arp entries";
                    }
                }
                case static {
                    leaf static {
                        type empty;
                        description
                            "This input queries for all the static
                             arp entries";
                    }
                }
                case ip {
                    leaf ip-address {
                        type inet:ipv4-address;
                        description
                            "This input queries for all the arp
                            entries for this ip address";
                    }
                }
            }
        }
        output {
            list arp-entry {
                key "ip-address";
                leaf ip-address {
                    type inet:ipv4-address;
                    description
                        "IP address of the ARP entry";
                }
                leaf mac-address {
                    type mac-access-list:mac-address-type;
                    description 
                        "Mac address of the ARP entry";
                }
                uses interface:interface-name-info;
                leaf is-resolved {
                    type boolean;
                    description
                        "This indicates whether the arp entry is
                         resolved or not";
                }
                leaf age {
                    type string;
                    description 
                        "This indicates the age of the arp entry";
                }
                leaf entry-type {
                    type enumeration {
                        enum static {
                            value 1;
                        }
                        enum dynamic {
                            value 2;
                        }
                        enum unknown {
                            value 3;
                        }
                    }
                    description
                        "This indicates the type of the arp entry";
                }
            }
        }
    }
}
