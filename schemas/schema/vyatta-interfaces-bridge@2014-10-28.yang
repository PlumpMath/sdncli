module vyatta-interfaces-bridge {
	namespace "urn:vyatta.com:mgmt:vyatta-interfaces-bridge";
	prefix interfaces-bridge;

	import vyatta-interfaces {
		prefix if;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /if:interfaces {
		list bridge {
			configd:priority "310";
			configd:help "Bridge interface name";
			configd:create "/opt/vyatta/share/tmplscripts/interfaces/bridge/configd_create.sh";
			configd:delete "/opt/vyatta/share/tmplscripts/interfaces/bridge/configd_delete.sh";
			key "tagnode";
			leaf tagnode {
				type string {
					pattern "br[0-9]+" {
						error-message "Must be (br0 - br999)";
					}
					configd:pattern-help "<brN>";
				}
				configd:help "Bridge interface name";
			}
			leaf priority {
				type uint32 {
					range 0..65535 {
						error-message "Bridge priority must be between 0 and 65535";
					}
				}
				configd:help "Priority for this bridge";
				default "0";
				configd:update "/opt/vyatta/share/tmplscripts/interfaces/bridge/priority/configd_update.sh";
				configd:delete "/opt/vyatta/share/tmplscripts/interfaces/bridge/priority/configd_delete.sh";
			}
			leaf description {
				type string {
					pattern ".{1,256}" {
						error-message "interface description is too long (limit 256 characters)";
					}
				}
				configd:help "Description";
				configd:update "/opt/vyatta/share/tmplscripts/interfaces/bridge/description/configd_update.sh";
				configd:delete "/opt/vyatta/share/tmplscripts/interfaces/bridge/description/configd_delete.sh";
			}
			container dhcpv6-options {
				presence "true";
				configd:priority "317";
				configd:help "DHCPv6 options";
				configd:end "/opt/vyatta/share/tmplscripts/interfaces/bridge/dhcpv6-options/configd_end.sh";
				leaf parameters-only {
					type empty;
					configd:help "Acquire only config parameters, not address";
				}
				leaf temporary {
					type empty;
					configd:help "IPv6 \"temporary\" address";
				}
			}
			leaf max-age {
				type uint32 {
					range 6..200 {
						error-message "Bridge max aging value must be between 6 and 200";
					}
				}
				configd:help "Interval at which neighbor bridges are removed";
				default "20";
				configd:update "/opt/vyatta/share/tmplscripts/interfaces/bridge/max-age/configd_update.sh";
				configd:delete "/opt/vyatta/share/tmplscripts/interfaces/bridge/max-age/configd_delete.sh";
			}
			leaf forwarding-delay {
				type uint32 {
					range 0..200 {
						error-message "Forwarding delay must be between 0 and 200";
					}
				}
				configd:help "Forwarding delay";
				configd:update "/opt/vyatta/share/tmplscripts/interfaces/bridge/forwarding-delay/configd_update.sh";
			}
			leaf disable {
				type empty;
				configd:help "Disable the bridge interface";
				configd:create "/opt/vyatta/share/tmplscripts/interfaces/bridge/disable/configd_create.sh";
				configd:delete "/opt/vyatta/share/tmplscripts/interfaces/bridge/disable/configd_delete.sh";
			}
			leaf-list address {
				type if:address-dhcp;
				ordered-by "user";
				configd:priority "320";
				configd:help "IP address";
				configd:create "/opt/vyatta/share/tmplscripts/interfaces/bridge/address/configd_create.sh";
				configd:allowed "/opt/vyatta/share/tmplscripts/interfaces/bridge/address/configd_allowed.sh";
			}
			leaf mac {
				type types:mac-address {
					configd:syntax "/opt/vyatta/share/tmplscripts/interfaces/bridge/mac/configd_syntax1.cli";
				}
				configd:help "Media Access Control (MAC) address";
			}
			leaf disable-link-detect {
				type empty;
				configd:help "Ignore link state changes";
				configd:create "/opt/vyatta/share/tmplscripts/interfaces/bridge/disable-link-detect/configd_create.sh";
				configd:delete "/opt/vyatta/share/tmplscripts/interfaces/bridge/disable-link-detect/configd_delete.sh";
			}
			leaf aging {
				type uint32 {
					configd:syntax "/opt/vyatta/share/tmplscripts/interfaces/bridge/aging/configd_syntax1.cli";
				}
				configd:help "Interval addresses are retained";
				default "300";
				configd:update "/opt/vyatta/share/tmplscripts/interfaces/bridge/aging/configd_update.sh";
				configd:delete "/opt/vyatta/share/tmplscripts/interfaces/bridge/aging/configd_delete.sh";
			}
			leaf hello-time {
				type uint32 {
					range 0..30 {
						error-message "Bridge Hello interval must be between 0 and 30 seconds";
					}
				}
				default "2";
				configd:help "Hello packet advertisment interval";
				configd:update "/opt/vyatta/share/tmplscripts/interfaces/bridge/hello-time/configd_update.sh";
				configd:delete "/opt/vyatta/share/tmplscripts/interfaces/bridge/hello-time/configd_delete.sh";
			}
			leaf stp {
				type boolean;
				default "false";
				configd:help "Enable spanning tree protocol";
				configd:update "/opt/vyatta/share/tmplscripts/interfaces/bridge/stp/configd_update.sh";
				configd:delete "/opt/vyatta/share/tmplscripts/interfaces/bridge/stp/configd_delete.sh";
			}
			container ip {
				configd:help "IPv4 parameters";
			}
			container ipv6 {
				presence "true";
				configd:help "IPv6 parameters";
			}
		}
	}
}
