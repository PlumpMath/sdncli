module vyatta-system-acm-opd {
	namespace "urn:vyatta.com:mgmt:vyatta-system-acm-opd";
	prefix system-acm-opd;

	import vyatta-system {
		prefix system;
	}
	import vyatta-system-acm {
		prefix system-acm;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-08-26 {
		description "Initial revision.";
		configd:migration 1;
	}

	augment /system:system/system-acm:acm {
		leaf exec-default {
			type enumeration {
				enum "allow" {
					configd:help "Allow the action";
				}
				enum "deny" {
					configd:help "Deny the action";
				}
			}
			default "allow";
			configd:help "Execute operation default action";
			configd:allowed "/opt/vyatta/share/tmplscripts/system/acm/exec-default/configd_allowed.sh";
		}
		container operational-ruleset {
			presence "true";
			configd:help "Operational command ruleset";
			list rule {
				configd:help "Rule number (1-9999)";
				configd:validate "/opt/vyatta/share/tmplscripts/system/acm/operational-ruleset/rule/configd_validate1.cli";
				configd:validate "/opt/vyatta/share/tmplscripts/system/acm/operational-ruleset/rule/configd_validate2.cli";
				key "tagnode";
				leaf tagnode {
					type uint32 {
						range 1..9999 {
							error-message "Rule number must be between 1 and 9999";
						}
					}
					configd:help "Rule number (1-9999)";
				}
				leaf action {
					type enumeration {
						enum "allow" {
							configd:help "Allow the action";
						}
						enum "deny" {
							configd:help "Deny the action";
						}
					}
					default "deny";
					configd:help "Action";
					configd:allowed "/opt/vyatta/share/tmplscripts/system/acm/operational-ruleset/rule/action/configd_allowed.sh";
				}
				leaf command {
					type string;
					configd:help "Path to match";
				}
				leaf-list group {
					type string;
					ordered-by "user";
					configd:help "Group to match";
					configd:allowed "/opt/vyatta/share/tmplscripts/system/acm/operational-ruleset/rule/group/configd_allowed.sh";
				}
				leaf log {
					type empty;
					configd:help "Enable logging for rule";
				}
			}
		}
	}
}
