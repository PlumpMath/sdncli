// YANG module for Netiron statedata definitions.
// Revisions:
//     2011-04-20: Initial version.
//

module netiron-statedata 
{
    namespace "http://brocade.com/ns/netconf/config/netiron-config/";
    prefix "statedata";

    include vlan-statedata;
    include interface-statedata;
    include mpls-statedata;

    organization
    	"Brocade Communications Inc.";

    contact
             "Technical Support Center"+
             "130 Holger Way,"+
             "San Jose, CA  95134"+
             "Email:  ipsupport@brocade.com"+
             "Phone: 1-800-752-8061"+
             "URL:  www.brocade.com";

    description
    	"NetIron device state data module. VERSION: V5.8.00a";
    
    revision 2011-04-20
    {
    	description "Initial revision";
    }
    
    grouping netiron-statedata
    {
        description "NetIron device state data group";
        container netiron-statedata
        {
            description "NetIron device state data";
			config false;
            uses vlan-statedata-grouping;
            uses interface-statedata-grouping;
            uses mpls-statedata-grouping;
        }
    }
}
