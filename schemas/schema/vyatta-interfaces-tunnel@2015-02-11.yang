module vyatta-interfaces-tunnel {
	namespace "urn:vyatta.com:mgmt:vyatta-interfaces-tunnel";
	prefix interfaces-tunnel;

	import vyatta-interfaces {
		prefix if;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-02-11 {
		description "Add path-mtu-discovery-disable to tunnels";
	}

	revision 2015-01-23 {
		description "Remove range restriction on IP key field";
	}

	revision 2014-10-28 {
		description "Update for 3.2.1R1";
	}
	
	revision 2014-08-27 {
		description "Initial revision.";
		configd:migration 1;
	}

	augment /if:interfaces {
		list tunnel {
			configd:priority "380";
			configd:help "Tunnel interface";
			configd:create "/opt/vyatta/share/tmplscripts/interfaces/tunnel/configd_create.sh";
			configd:delete "/opt/vyatta/share/tmplscripts/interfaces/tunnel/configd_delete.sh";
			configd:end "/opt/vyatta/share/tmplscripts/interfaces/tunnel/configd_end.sh";
			configd:validate "/opt/vyatta/share/tmplscripts/interfaces/tunnel/configd_validate1.cli";
			configd:validate "/opt/vyatta/share/tmplscripts/interfaces/tunnel/configd_validate2.cli";
			configd:validate "/opt/vyatta/share/tmplscripts/interfaces/tunnel/configd_validate3.cli";
			configd:validate "/opt/vyatta/share/tmplscripts/interfaces/tunnel/configd_validate4.cli";
			configd:validate "/opt/vyatta/share/tmplscripts/interfaces/tunnel/configd_validate5.cli";
			key "tagnode";
			leaf tagnode {
				type string {
					pattern "tun[0-9]+" {
						error-message "tunnel must be (tun0-tun999)";
					}
					configd:pattern-help "<tunN>";
				}
				configd:help "Tunnel interface";
			}
			container parameters {
				presence "true";
				configd:help "Tunnel parameters";
				container ip {
					presence "true";
					configd:help "IPv4 specific tunnel parameters";
					leaf ttl {
						type uint32 {
							range 0..255 {
								error-message "Must be between 0-255";
							}
						}
						configd:help "Time to live field";
						configd:update "/opt/vyatta/share/tmplscripts/interfaces/tunnel/parameters/ip/ttl/configd_update.sh";
						configd:delete "/opt/vyatta/share/tmplscripts/interfaces/tunnel/parameters/ip/ttl/configd_delete.sh";
						configd:validate "/opt/vyatta/share/tmplscripts/interfaces/tunnel/parameters/ip/ttl/configd_validate1.cli";
					}
					leaf key {
						type uint32 {
						    configd:syntax "/opt/vyatta/share/tmplscripts/interfaces/tunnel/parameters/ip/key/configd_syntax1.cli";
						}
						configd:help "Tunnel key";
						configd:validate "/opt/vyatta/share/tmplscripts/interfaces/tunnel/parameters/ip/key/configd_validate1.cli";
						configd:create "/opt/vyatta/share/tmplscripts/interfaces/tunnel/parameters/ip/key/configd_create1.cli";
						configd:update "/opt/vyatta/share/tmplscripts/interfaces/tunnel/parameters/ip/key/configd_update1.cli";
					}
					container bridge-group {
						presence "true";
						configd:help "Add this interface to a bridge group";
						leaf priority {
							type uint32 {
								range 0..63 {
									error-message "Port priority must be between 0-63";
								}
							}
							configd:help "Bridge port priority";
						}
						leaf bridge {
							type string;
							configd:help "Bridge group interface";
							configd:allowed "/opt/vyatta/share/tmplscripts/interfaces/tunnel/parameters/ip/bridge-group/bridge/configd_allowed.sh";
							configd:create "/opt/vyatta/share/tmplscripts/interfaces/tunnel/parameters/ip/bridge-group/bridge/configd_create.sh";
							configd:delete "/opt/vyatta/share/tmplscripts/interfaces/tunnel/parameters/ip/bridge-group/bridge/configd_delete.sh";
							configd:validate "/opt/vyatta/share/tmplscripts/interfaces/tunnel/parameters/ip/bridge-group/bridge/configd_validate1.cli";
							configd:validate "/opt/vyatta/share/tmplscripts/interfaces/tunnel/parameters/ip/bridge-group/bridge/configd_validate2.cli";
						}
						leaf cost {
							type uint32 {
								range 1..65535 {
									error-message "Bridge cost value must be between 1 and 65535";
								}
							}
							configd:help "Path cost for this port";
						}
					}
					leaf tos {
						type uint32 {
							range 0..99 {
								error-message "Must be between 0-99";
							}
						}
						configd:help "Type of Service (TOS)";
						configd:update "/opt/vyatta/share/tmplscripts/interfaces/tunnel/parameters/ip/tos/configd_update.sh";
						configd:delete "/opt/vyatta/share/tmplscripts/interfaces/tunnel/parameters/ip/tos/configd_delete.sh";
						configd:validate "/opt/vyatta/share/tmplscripts/interfaces/tunnel/parameters/ip/tos/configd_validate1.cli";
					}
				}
				container ipv6 {
					presence "true";
					configd:help "IPv6 specific tunnel parameters";
					configd:delete "/opt/vyatta/share/tmplscripts/interfaces/tunnel/parameters/ipv6/configd_delete.sh";
					leaf tclass {
						type string {
							configd:syntax "/opt/vyatta/share/tmplscripts/interfaces/tunnel/parameters/ipv6/tclass/configd_syntax1.cli";
						}
						configd:help "Traffic class (Tclass)";
						default "0x00";
						configd:update "/opt/vyatta/share/tmplscripts/interfaces/tunnel/parameters/ipv6/tclass/configd_update.sh";
					}
					leaf hoplimit {
						type uint32 {
							range 0..255 {
								error-message "Must be between 0-255";
							}
						}
						configd:help "Hoplimit";
						default "64";
						configd:update "/opt/vyatta/share/tmplscripts/interfaces/tunnel/parameters/ipv6/hoplimit/configd_update.sh";
					}
					leaf encaplimit {
						type string {
							configd:syntax "/opt/vyatta/share/tmplscripts/interfaces/tunnel/parameters/ipv6/encaplimit/configd_syntax1.cli";
						}
						configd:help "Encaplimit field";
						default "4";
						configd:update "/opt/vyatta/share/tmplscripts/interfaces/tunnel/parameters/ipv6/encaplimit/configd_update.sh";
					}
					leaf flowlabel {
						type string {
							configd:syntax "/opt/vyatta/share/tmplscripts/interfaces/tunnel/parameters/ipv6/flowlabel/configd_syntax1.cli";
						}
						configd:help "Flowlabel";
						default "0x00000";
						configd:update "/opt/vyatta/share/tmplscripts/interfaces/tunnel/parameters/ipv6/flowlabel/configd_update.sh";
					}
				}
			}
			leaf local-ip {
				type union {
					type types:ipv4-address;
					type types:ipv6-address;
				}
				configd:help "Local IP address for this tunnel [REQUIRED]";
				configd:update "/opt/vyatta/share/tmplscripts/interfaces/tunnel/local-ip/configd_update.sh";
			}
			leaf description {
				type string {
					pattern ".{1,256}" {
						error-message "interface description is too long (limit 256 characters)";
					}
				}
				configd:help "Description";
				configd:update "/opt/vyatta/share/tmplscripts/interfaces/tunnel/description/configd_update.sh";
				configd:delete "/opt/vyatta/share/tmplscripts/interfaces/tunnel/description/configd_delete.sh";
			}
			leaf mtu {
				type uint32 {
					range 68..8024 {
						error-message "MTU must be between 68 and 8024";
					}
				}
				configd:priority "381";
				configd:help "Maximum Transmission Unit (MTU)";
				configd:update "/opt/vyatta/share/tmplscripts/interfaces/tunnel/mtu/configd_update.sh";
				configd:delete "/opt/vyatta/share/tmplscripts/interfaces/tunnel/mtu/configd_delete.sh";
			}
			leaf multicast {
				type enumeration {
					enum "enable" {
						configd:help "Enable Multicast";
					}
					enum "disable" {
						configd:help "Disable Multicast (default)";
					}
				}
				configd:help "Multicast operation over tunnel";
				default "disable";
				configd:allowed "/opt/vyatta/share/tmplscripts/interfaces/tunnel/multicast/configd_allowed.sh";
				configd:update "/opt/vyatta/share/tmplscripts/interfaces/tunnel/multicast/configd_update.sh";
			}
			leaf path-mtu-discovery-disable {
				type empty;
				configd:help "Disable pmtu discovery support";
				configd:update "/opt/vyatta/share/tmplscripts/interfaces/tunnel/pmtudisc/configd_update.sh";
				configd:delete "/opt/vyatta/share/tmplscripts/interfaces/tunnel/pmtudisc/configd_delete.sh";
				configd:validate "/opt/vyatta/share/tmplscripts/interfaces/tunnel/pmtudisc/configd_validate1.sh";
			}
			leaf disable {
				type empty;
				configd:help "Disable interface";
				configd:create "/opt/vyatta/share/tmplscripts/interfaces/tunnel/disable/configd_create.sh";
				configd:delete "/opt/vyatta/share/tmplscripts/interfaces/tunnel/disable/configd_delete.sh";
			}
			leaf remote-ip {
				type union {
					type types:ipv4-address;
					type types:ipv6-address;
				}
				configd:help "Remote IP address for this tunnel";
				configd:update "/opt/vyatta/share/tmplscripts/interfaces/tunnel/remote-ip/configd_update.sh";
			}
			leaf-list address {
				type if:address;
				ordered-by "user";
				configd:help "IP address";
				configd:create "/opt/vyatta/share/tmplscripts/interfaces/tunnel/address/configd_create.sh";
			}
			leaf disable-link-detect {
				type empty;
				configd:help "Ignore link state changes";
				configd:create "/opt/vyatta/share/tmplscripts/interfaces/tunnel/disable-link-detect/configd_create.sh";
				configd:delete "/opt/vyatta/share/tmplscripts/interfaces/tunnel/disable-link-detect/configd_delete.sh";
			}
			leaf encapsulation {
				type string {
					configd:syntax "/opt/vyatta/share/tmplscripts/interfaces/tunnel/encapsulation/configd_syntax1.cli";
				}
				configd:help "Encapsulation of this tunnel interface [REQUIRED]";
				configd:allowed "/opt/vyatta/share/tmplscripts/interfaces/tunnel/encapsulation/configd_allowed.sh";
				configd:create "/opt/vyatta/share/tmplscripts/interfaces/tunnel/encapsulation/configd_create1.cli";
				configd:update "/opt/vyatta/share/tmplscripts/interfaces/tunnel/encapsulation/configd_update1.cli";
			}
			container ip {
				configd:help "IPv4 parameters";
			}
			container ipv6 {
				presence "true";
				configd:help "IPv6 parameters";
			}
		}
	}
}
