module vyatta-system {
	namespace "urn:vyatta.com:mgmt:vyatta-system";
	prefix system;

	import configd { prefix configd; }

	organization "Brocade Communications Systems, Inc.";
	contact
		"Brocade Communications Systems, Inc.
		 Postal: 130 Holger Way
		 	 San Jose, CA 95134
		 E-mail: support@Brocade.com
		 Web: www.brocade.com";
	revision 2014-05-30 {
		description "Initial revision.";
	}

	container system {
		presence "true";
		configd:help "System parameters";
	}
}
