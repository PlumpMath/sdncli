module vyatta-service-connsync {
	namespace "urn:vyatta.com:mgmt:vyatta-service-connsync";
	prefix service-connsync;

	import vyatta-types {
		prefix types;
	}
	import vyatta-services {
		prefix service;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-08-27 {
		description "Initial revision.";
		configd:migration 1;
	}

	augment /service:service {
		container connsync {
			presence "true";
			configd:help "Connection tracking synchronization (conn-sync) service";
			configd:priority "995";
			configd:end "/opt/vyatta/share/tmplscripts/service/connsync/configd_end.sh";
			leaf interface {
				type string;
				configd:help "Interface to use for syncing flow entries [REQUIRED]";
				configd:allowed "/opt/vyatta/share/tmplscripts/service/connsync/interface/configd_allowed.sh";
			}
			leaf remote-peer {
				type types:ipv4-address;
				configd:help "IP address";
			}
			container failover-mechanism {
				presence "true";
				configd:help "Failover mechanism to use for conntrack-sync [REQUIRED]";
				container vrrp {
					presence "true";
					configd:help "VRRP as failover-mechanism to use for conn-sync";
					leaf sync-group {
						type string;
						configd:help "VRRP sync group [REQUIRED]";
						configd:allowed "/opt/vyatta/sbin/vyatta-connsync.pl --action=vrrp-sync-grps";
					}
				}
			}
		}
	}
}
