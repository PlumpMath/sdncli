module vyatta-protocols-mld {
	namespace "urn:vyatta.com:mgmt:vyatta-protocols-mld";
	prefix protocols-mld;

	import vyatta-types {
		prefix types;
	}
	import vyatta-protocols {
		prefix protocols;
	}
	import configd {
		prefix configd;
	}
	import vyatta-interfaces {
		prefix if;
	}
	import vyatta-interfaces-bridge {
		prefix interfaces-bridge;
	}
	import vyatta-interfaces-dataplane {
		prefix interfaces-dataplane;
	}
	import vyatta-interfaces-l2tpeth {
		prefix interfaces-l2tpeth;
	}
	import vyatta-interfaces-loopback {
		prefix interfaces-loopback;
	}
	import vyatta-interfaces-openvpn {
		prefix interfaces-openvpn;
	}
	import vyatta-interfaces-tunnel {
		prefix interfaces-tunnel;
	}
	import vyatta-interfaces-vti {
		prefix interfaces-vti;
	}

	organization "Brocade Communications Systems, Inc.";
	contact
		"Brocade Communications Systems, Inc.
		 Postal: 130 Holger Way
		         San Jose, CA 95134
		 E-mail: support@Brocade.com
		 Web: www.brocade.com";

	revision 2014-08-27 {
		description "Initial revision.";
		configd:migration 1;
	}

	augment /protocols:protocols {
		container mld {
			presence "true";
			configd:priority "770";
			configd:help "Multicast Listener Discovery (MLD)";
			configd:validate "/opt/vyatta/share/tmplscripts/protocols/mld/configd_validate1.cli";
			leaf limit-exception {
				type string {
					configd:syntax "/opt/vyatta/share/tmplscripts/protocols/mld/limit-exception/configd_syntax1.cli";
				}
				configd:help "Specify access-list that defines multicast groups that are exempted from being subject to configured limit";
				configd:allowed "/opt/vyatta/share/tmplscripts/protocols/mld/limit-exception/configd_allowed.sh";
				configd:update "/opt/vyatta/share/tmplscripts/protocols/mld/limit-exception/configd_update.sh";
				configd:delete "/opt/vyatta/share/tmplscripts/protocols/mld/limit-exception/configd_delete.sh";
				configd:validate "/opt/vyatta/share/tmplscripts/protocols/mld/limit-exception/configd_validate1.cli";
				configd:validate "/opt/vyatta/share/tmplscripts/protocols/mld/limit-exception/configd_validate2.cli";
			}
			leaf limit {
				type uint32 {
					range 1..2097152 {
						error-message "Must be between 1-2097152";
					}
				}
				configd:help "Configure the limit on the maximum number of group membership states";
				configd:update "/opt/vyatta/share/tmplscripts/protocols/mld/limit/configd_update.sh";
				configd:delete "/opt/vyatta/share/tmplscripts/protocols/mld/limit/configd_delete.sh";
			}
			container ssm-map {
				presence "true";
				configd:help "Enable SSM mapping on the router";
				configd:create "/opt/vyatta/share/tmplscripts/protocols/mld/ssm-map/configd_create.sh";
				configd:delete "/opt/vyatta/share/tmplscripts/protocols/mld/ssm-map/configd_delete.sh";
				container static {
					presence "true";
					configd:help "Configure the static mode of defining SSM mapping";
					configd:validate "/opt/vyatta/share/tmplscripts/protocols/mld/ssm-map/static/configd_validate1.cli";
					list access-list {
						configd:help "Configure access-list for the static mode of defining SSM mapping";
						configd:allowed "/opt/vyatta/share/tmplscripts/protocols/mld/ssm-map/static/access-list/configd_allowed.sh";
						configd:validate "/opt/vyatta/share/tmplscripts/protocols/mld/ssm-map/static/access-list/configd_validate1.cli";
						configd:validate "/opt/vyatta/share/tmplscripts/protocols/mld/ssm-map/static/access-list/configd_validate2.cli";
						key "tagnode";
						leaf tagnode {
							type string {
								configd:syntax "/opt/vyatta/share/tmplscripts/protocols/mld/ssm-map/static/access-list/configd_syntax1.cli";
							}
							configd:help "Configure access-list for the static mode of defining SSM mapping";
							configd:allowed "/opt/vyatta/share/tmplscripts/protocols/mld/ssm-map/static/access-list/configd_allowed.sh";
						}
						leaf-list source {
							type types:ipv6-address;
							ordered-by "user";
							configd:help "Configure IPv6 source address to use for static map group";
							configd:create "/opt/vyatta/share/tmplscripts/protocols/mld/ssm-map/static/access-list/source/configd_create.sh";
							configd:delete "/opt/vyatta/share/tmplscripts/protocols/mld/ssm-map/static/access-list/source/configd_delete.sh";
						}
					}
				}
			}
		}
	}
	augment /if:interfaces/interfaces-bridge:bridge/interfaces-bridge:ipv6 {
		container mld {
			presence "true";
			configd:priority "960";
			configd:help "Multicast Listener Discovery (MLD)";
			configd:end "/opt/vyatta/share/tmplscripts/interfaces/bridge/ipv6/mld/configd_end.sh";
			configd:validate "/opt/vyatta/share/tmplscripts/interfaces/bridge/ipv6/mld/configd_validate1.cli";
			configd:validate "/opt/vyatta/share/tmplscripts/interfaces/bridge/ipv6/mld/configd_validate2.cli";
			configd:validate "/opt/vyatta/share/tmplscripts/interfaces/bridge/ipv6/mld/configd_validate3.cli";
			container immediate-leave {
				presence "true";
				configd:help "Immediate leave feature";
				configd:validate "/opt/vyatta/share/tmplscripts/interfaces/bridge/ipv6/mld/immediate-leave/configd_validate1.cli";
				leaf group-list {
					type string;
					configd:help "Define multicast groups in which the immediate leave feature is enabled";
					configd:allowed "/opt/vyatta/share/tmplscripts/interfaces/bridge/ipv6/mld/immediate-leave/group-list/configd_allowed.sh";
					configd:update "/opt/vyatta/share/tmplscripts/interfaces/bridge/ipv6/mld/immediate-leave/group-list/configd_update.sh";
					configd:delete "/opt/vyatta/share/tmplscripts/interfaces/bridge/ipv6/mld/immediate-leave/group-list/configd_delete.sh";
					configd:validate "/opt/vyatta/share/tmplscripts/interfaces/bridge/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/bridge/ipv6/mld/robustness-variable/configd_update.sh";
				configd:delete "/opt/vyatta/share/tmplscripts/interfaces/bridge/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/bridge/ipv6/mld/querier-timeout/configd_update.sh";
				configd:delete "/opt/vyatta/share/tmplscripts/interfaces/bridge/ipv6/mld/querier-timeout/configd_delete.sh";
			}
			leaf limit-exception {
				type string;
				configd:help "Specify access-list that defines multicast groups that are exempted from being subject to configured limit";
				configd:allowed "/opt/vyatta/share/tmplscripts/interfaces/bridge/ipv6/mld/limit-exception/configd_allowed.sh";
				configd:update "/opt/vyatta/share/tmplscripts/interfaces/bridge/ipv6/mld/limit-exception/configd_update.sh";
				configd:delete "/opt/vyatta/share/tmplscripts/interfaces/bridge/ipv6/mld/limit-exception/configd_delete.sh";
				configd:validate "/opt/vyatta/share/tmplscripts/interfaces/bridge/ipv6/mld/limit-exception/configd_validate1.cli";
				configd:validate "/opt/vyatta/share/tmplscripts/interfaces/bridge/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/bridge/ipv6/mld/limit/configd_update.sh";
				configd:delete "/opt/vyatta/share/tmplscripts/interfaces/bridge/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/bridge/ipv6/mld/query-max-response-time/configd_delete.sh";
				configd:validate "/opt/vyatta/share/tmplscripts/interfaces/bridge/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/bridge/ipv6/mld/last-member-query-count/configd_update.sh";
				configd:delete "/opt/vyatta/share/tmplscripts/interfaces/bridge/ipv6/mld/last-member-query-count/configd_delete.sh";
			}
			list static-group {
				configd:help "Set standard IPv6 Multicast group address to be configured as a static group member";
				configd:create "/opt/vyatta/share/tmplscripts/interfaces/bridge/ipv6/mld/static-group/configd_create.sh";
				configd:end "/opt/vyatta/share/tmplscripts/interfaces/bridge/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/bridge/ipv6/mld/static-group/source/configd_syntax1.cli";
					}
					ordered-by "user";
					configd:help "Configure standard IPv6 source address as a static source from where multicast packets originate";
					configd:allowed "/opt/vyatta/share/tmplscripts/interfaces/bridge/ipv6/mld/static-group/source/configd_allowed.sh";
					configd:create "/opt/vyatta/share/tmplscripts/interfaces/bridge/ipv6/mld/static-group/source/configd_create.sh";
					configd:delete "/opt/vyatta/share/tmplscripts/interfaces/bridge/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/bridge/ipv6/mld/last-member-query-interval/configd_update.sh";
				configd:delete "/opt/vyatta/share/tmplscripts/interfaces/bridge/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/bridge/ipv6/mld/version/configd_update.sh";
				configd:delete "/opt/vyatta/share/tmplscripts/interfaces/bridge/ipv6/mld/version/configd_delete.sh";
			}
			leaf access-group {
				type string;
				configd:help "Control the multicast local-membership groups learnt on an interface";
				configd:allowed "/opt/vyatta/share/tmplscripts/interfaces/bridge/ipv6/mld/access-group/configd_allowed.sh";
				configd:update "/opt/vyatta/share/tmplscripts/interfaces/bridge/ipv6/mld/access-group/configd_update.sh";
				configd:delete "/opt/vyatta/share/tmplscripts/interfaces/bridge/ipv6/mld/access-group/configd_delete.sh";
				configd:validate "/opt/vyatta/share/tmplscripts/interfaces/bridge/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/bridge/ipv6/mld/query-interval/configd_delete.sh";
				configd:validate "/opt/vyatta/share/tmplscripts/interfaces/bridge/ipv6/mld/query-interval/configd_validate1.cli";
			}
		}
	}
	augment /if:interfaces/interfaces-dataplane:dataplane/interfaces-dataplane:ipv6 {
		container mld {
			presence "true";
			configd:priority "960";
			configd:help "Multicast Listener Discovery (MLD)";
			configd:end "/opt/vyatta/share/tmplscripts/interfaces/dataplane/ipv6/mld/configd_end.sh";
			configd:validate "/opt/vyatta/share/tmplscripts/interfaces/dataplane/ipv6/mld/configd_validate1.cli";
			configd:validate "/opt/vyatta/share/tmplscripts/interfaces/dataplane/ipv6/mld/configd_validate2.cli";
			configd:validate "/opt/vyatta/share/tmplscripts/interfaces/dataplane/ipv6/mld/configd_validate3.cli";
			container immediate-leave {
				presence "true";
				configd:help "Immediate leave feature";
				configd:validate "/opt/vyatta/share/tmplscripts/interfaces/dataplane/ipv6/mld/immediate-leave/configd_validate1.cli";
				leaf group-list {
					type string;
					configd:help "Define multicast groups in which the immediate leave feature is enabled";
					configd:allowed "/opt/vyatta/share/tmplscripts/interfaces/dataplane/ipv6/mld/immediate-leave/group-list/configd_allowed.sh";
					configd:update "/opt/vyatta/share/tmplscripts/interfaces/dataplane/ipv6/mld/immediate-leave/group-list/configd_update.sh";
					configd:delete "/opt/vyatta/share/tmplscripts/interfaces/dataplane/ipv6/mld/immediate-leave/group-list/configd_delete.sh";
					configd:validate "/opt/vyatta/share/tmplscripts/interfaces/dataplane/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/dataplane/ipv6/mld/robustness-variable/configd_update.sh";
				configd:delete "/opt/vyatta/share/tmplscripts/interfaces/dataplane/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/dataplane/ipv6/mld/querier-timeout/configd_update.sh";
				configd:delete "/opt/vyatta/share/tmplscripts/interfaces/dataplane/ipv6/mld/querier-timeout/configd_delete.sh";
			}
			leaf limit-exception {
				type string;
				configd:help "Specify access-list that defines multicast groups that are exempted from being subject to configured limit";
				configd:allowed "/opt/vyatta/share/tmplscripts/interfaces/dataplane/ipv6/mld/limit-exception/configd_allowed.sh";
				configd:update "/opt/vyatta/share/tmplscripts/interfaces/dataplane/ipv6/mld/limit-exception/configd_update.sh";
				configd:delete "/opt/vyatta/share/tmplscripts/interfaces/dataplane/ipv6/mld/limit-exception/configd_delete.sh";
				configd:validate "/opt/vyatta/share/tmplscripts/interfaces/dataplane/ipv6/mld/limit-exception/configd_validate1.cli";
				configd:validate "/opt/vyatta/share/tmplscripts/interfaces/dataplane/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/dataplane/ipv6/mld/limit/configd_update.sh";
				configd:delete "/opt/vyatta/share/tmplscripts/interfaces/dataplane/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/dataplane/ipv6/mld/query-max-response-time/configd_delete.sh";
				configd:validate "/opt/vyatta/share/tmplscripts/interfaces/dataplane/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/dataplane/ipv6/mld/last-member-query-count/configd_update.sh";
				configd:delete "/opt/vyatta/share/tmplscripts/interfaces/dataplane/ipv6/mld/last-member-query-count/configd_delete.sh";
			}
			list static-group {
				configd:help "Set standard IPv6 Multicast group address to be configured as a static group member";
				configd:create "/opt/vyatta/share/tmplscripts/interfaces/dataplane/ipv6/mld/static-group/configd_create.sh";
				configd:end "/opt/vyatta/share/tmplscripts/interfaces/dataplane/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/dataplane/ipv6/mld/static-group/source/configd_syntax1.cli";
					}
					ordered-by "user";
					configd:help "Configure standard IPv6 source address as a static source from where multicast packets originate";
					configd:allowed "/opt/vyatta/share/tmplscripts/interfaces/dataplane/ipv6/mld/static-group/source/configd_allowed.sh";
					configd:create "/opt/vyatta/share/tmplscripts/interfaces/dataplane/ipv6/mld/static-group/source/configd_create.sh";
					configd:delete "/opt/vyatta/share/tmplscripts/interfaces/dataplane/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/dataplane/ipv6/mld/last-member-query-interval/configd_update.sh";
				configd:delete "/opt/vyatta/share/tmplscripts/interfaces/dataplane/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/dataplane/ipv6/mld/version/configd_update.sh";
				configd:delete "/opt/vyatta/share/tmplscripts/interfaces/dataplane/ipv6/mld/version/configd_delete.sh";
			}
			leaf access-group {
				type string;
				configd:help "Control the multicast local-membership groups learnt on an interface";
				configd:allowed "/opt/vyatta/share/tmplscripts/interfaces/dataplane/ipv6/mld/access-group/configd_allowed.sh";
				configd:update "/opt/vyatta/share/tmplscripts/interfaces/dataplane/ipv6/mld/access-group/configd_update.sh";
				configd:delete "/opt/vyatta/share/tmplscripts/interfaces/dataplane/ipv6/mld/access-group/configd_delete.sh";
				configd:validate "/opt/vyatta/share/tmplscripts/interfaces/dataplane/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/dataplane/ipv6/mld/query-interval/configd_delete.sh";
				configd:validate "/opt/vyatta/share/tmplscripts/interfaces/dataplane/ipv6/mld/query-interval/configd_validate1.cli";
			}
		}
	}
	augment /if:interfaces/interfaces-dataplane:dataplane/interfaces-dataplane:vif/interfaces-dataplane:ipv6 {
		container mld {
			presence "true";
			configd:priority "960";
			configd:help "Multicast Listener Discovery (MLD)";
			configd:end "/opt/vyatta/share/tmplscripts/interfaces/dataplane/vif/ipv6/mld/configd_end.sh";
			configd:validate "/opt/vyatta/share/tmplscripts/interfaces/dataplane/vif/ipv6/mld/configd_validate1.cli";
			configd:validate "/opt/vyatta/share/tmplscripts/interfaces/dataplane/vif/ipv6/mld/configd_validate2.cli";
			configd:validate "/opt/vyatta/share/tmplscripts/interfaces/dataplane/vif/ipv6/mld/configd_validate3.cli";
			container immediate-leave {
				presence "true";
				configd:help "Immediate leave feature";
				configd:validate "/opt/vyatta/share/tmplscripts/interfaces/dataplane/vif/ipv6/mld/immediate-leave/configd_validate1.cli";
				leaf group-list {
					type string;
					configd:help "Define multicast groups in which the immediate leave feature is enabled";
					configd:allowed "/opt/vyatta/share/tmplscripts/interfaces/dataplane/vif/ipv6/mld/immediate-leave/group-list/configd_allowed.sh";
					configd:update "/opt/vyatta/share/tmplscripts/interfaces/dataplane/vif/ipv6/mld/immediate-leave/group-list/configd_update.sh";
					configd:delete "/opt/vyatta/share/tmplscripts/interfaces/dataplane/vif/ipv6/mld/immediate-leave/group-list/configd_delete.sh";
					configd:validate "/opt/vyatta/share/tmplscripts/interfaces/dataplane/vif/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/dataplane/vif/ipv6/mld/robustness-variable/configd_update.sh";
				configd:delete "/opt/vyatta/share/tmplscripts/interfaces/dataplane/vif/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/dataplane/vif/ipv6/mld/querier-timeout/configd_update.sh";
				configd:delete "/opt/vyatta/share/tmplscripts/interfaces/dataplane/vif/ipv6/mld/querier-timeout/configd_delete.sh";
			}
			leaf limit-exception {
				type string;
				configd:help "Specify access-list that defines multicast groups that are exempted from being subject to configured limit";
				configd:allowed "/opt/vyatta/share/tmplscripts/interfaces/dataplane/vif/ipv6/mld/limit-exception/configd_allowed.sh";
				configd:update "/opt/vyatta/share/tmplscripts/interfaces/dataplane/vif/ipv6/mld/limit-exception/configd_update.sh";
				configd:delete "/opt/vyatta/share/tmplscripts/interfaces/dataplane/vif/ipv6/mld/limit-exception/configd_delete.sh";
				configd:validate "/opt/vyatta/share/tmplscripts/interfaces/dataplane/vif/ipv6/mld/limit-exception/configd_validate1.cli";
				configd:validate "/opt/vyatta/share/tmplscripts/interfaces/dataplane/vif/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/dataplane/vif/ipv6/mld/limit/configd_update.sh";
				configd:delete "/opt/vyatta/share/tmplscripts/interfaces/dataplane/vif/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/dataplane/vif/ipv6/mld/query-max-response-time/configd_delete.sh";
				configd:validate "/opt/vyatta/share/tmplscripts/interfaces/dataplane/vif/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/dataplane/vif/ipv6/mld/last-member-query-count/configd_update.sh";
				configd:delete "/opt/vyatta/share/tmplscripts/interfaces/dataplane/vif/ipv6/mld/last-member-query-count/configd_delete.sh";
			}
			list static-group {
				configd:help "Set standard IPv6 Multicast group address to be configured as a static group member";
				configd:create "/opt/vyatta/share/tmplscripts/interfaces/dataplane/vif/ipv6/mld/static-group/configd_create.sh";
				configd:end "/opt/vyatta/share/tmplscripts/interfaces/dataplane/vif/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/dataplane/vif/ipv6/mld/static-group/source/configd_syntax1.cli";
					}
					ordered-by "user";
					configd:help "Configure standard IPv6 source address as a static source from where multicast packets originate";
					configd:allowed "/opt/vyatta/share/tmplscripts/interfaces/dataplane/vif/ipv6/mld/static-group/source/configd_allowed.sh";
					configd:create "/opt/vyatta/share/tmplscripts/interfaces/dataplane/vif/ipv6/mld/static-group/source/configd_create.sh";
					configd:delete "/opt/vyatta/share/tmplscripts/interfaces/dataplane/vif/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/dataplane/vif/ipv6/mld/last-member-query-interval/configd_update.sh";
				configd:delete "/opt/vyatta/share/tmplscripts/interfaces/dataplane/vif/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/dataplane/vif/ipv6/mld/version/configd_update.sh";
				configd:delete "/opt/vyatta/share/tmplscripts/interfaces/dataplane/vif/ipv6/mld/version/configd_delete.sh";
			}
			leaf access-group {
				type string;
				configd:help "Control the multicast local-membership groups learnt on an interface";
				configd:allowed "/opt/vyatta/share/tmplscripts/interfaces/dataplane/vif/ipv6/mld/access-group/configd_allowed.sh";
				configd:update "/opt/vyatta/share/tmplscripts/interfaces/dataplane/vif/ipv6/mld/access-group/configd_update.sh";
				configd:delete "/opt/vyatta/share/tmplscripts/interfaces/dataplane/vif/ipv6/mld/access-group/configd_delete.sh";
				configd:validate "/opt/vyatta/share/tmplscripts/interfaces/dataplane/vif/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/dataplane/vif/ipv6/mld/query-interval/configd_delete.sh";
				configd:validate "/opt/vyatta/share/tmplscripts/interfaces/dataplane/vif/ipv6/mld/query-interval/configd_validate1.cli";
			}
		}
	}
	augment /if:interfaces/interfaces-l2tpeth:l2tpeth/interfaces-l2tpeth:ipv6 {
		container mld {
			presence "true";
			configd:priority "960";
			configd:help "Multicast Listener Discovery (MLD)";
			configd:end "/opt/vyatta/share/tmplscripts/interfaces/l2tpeth/ipv6/mld/configd_end.sh";
			configd:validate "/opt/vyatta/share/tmplscripts/interfaces/l2tpeth/ipv6/mld/configd_validate1.cli";
			configd:validate "/opt/vyatta/share/tmplscripts/interfaces/l2tpeth/ipv6/mld/configd_validate2.cli";
			configd:validate "/opt/vyatta/share/tmplscripts/interfaces/l2tpeth/ipv6/mld/configd_validate3.cli";
			container immediate-leave {
				presence "true";
				configd:help "Immediate leave feature";
				configd:validate "/opt/vyatta/share/tmplscripts/interfaces/l2tpeth/ipv6/mld/immediate-leave/configd_validate1.cli";
				leaf group-list {
					type string;
					configd:help "Define multicast groups in which the immediate leave feature is enabled";
					configd:allowed "/opt/vyatta/share/tmplscripts/interfaces/l2tpeth/ipv6/mld/immediate-leave/group-list/configd_allowed.sh";
					configd:update "/opt/vyatta/share/tmplscripts/interfaces/l2tpeth/ipv6/mld/immediate-leave/group-list/configd_update.sh";
					configd:delete "/opt/vyatta/share/tmplscripts/interfaces/l2tpeth/ipv6/mld/immediate-leave/group-list/configd_delete.sh";
					configd:validate "/opt/vyatta/share/tmplscripts/interfaces/l2tpeth/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/l2tpeth/ipv6/mld/robustness-variable/configd_update.sh";
				configd:delete "/opt/vyatta/share/tmplscripts/interfaces/l2tpeth/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/l2tpeth/ipv6/mld/querier-timeout/configd_update.sh";
				configd:delete "/opt/vyatta/share/tmplscripts/interfaces/l2tpeth/ipv6/mld/querier-timeout/configd_delete.sh";
			}
			leaf limit-exception {
				type string;
				configd:help "Specify access-list that defines multicast groups that are exempted from being subject to configured limit";
				configd:allowed "/opt/vyatta/share/tmplscripts/interfaces/l2tpeth/ipv6/mld/limit-exception/configd_allowed.sh";
				configd:update "/opt/vyatta/share/tmplscripts/interfaces/l2tpeth/ipv6/mld/limit-exception/configd_update.sh";
				configd:delete "/opt/vyatta/share/tmplscripts/interfaces/l2tpeth/ipv6/mld/limit-exception/configd_delete.sh";
				configd:validate "/opt/vyatta/share/tmplscripts/interfaces/l2tpeth/ipv6/mld/limit-exception/configd_validate1.cli";
				configd:validate "/opt/vyatta/share/tmplscripts/interfaces/l2tpeth/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/l2tpeth/ipv6/mld/limit/configd_update.sh";
				configd:delete "/opt/vyatta/share/tmplscripts/interfaces/l2tpeth/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/l2tpeth/ipv6/mld/query-max-response-time/configd_delete.sh";
				configd:validate "/opt/vyatta/share/tmplscripts/interfaces/l2tpeth/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/l2tpeth/ipv6/mld/last-member-query-count/configd_update.sh";
				configd:delete "/opt/vyatta/share/tmplscripts/interfaces/l2tpeth/ipv6/mld/last-member-query-count/configd_delete.sh";
			}
			list static-group {
				configd:help "Set standard IPv6 Multicast group address to be configured as a static group member";
				configd:create "/opt/vyatta/share/tmplscripts/interfaces/l2tpeth/ipv6/mld/static-group/configd_create.sh";
				configd:end "/opt/vyatta/share/tmplscripts/interfaces/l2tpeth/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/l2tpeth/ipv6/mld/static-group/source/configd_syntax1.cli";
					}
					ordered-by "user";
					configd:help "Configure standard IPv6 source address as a static source from where multicast packets originate";
					configd:allowed "/opt/vyatta/share/tmplscripts/interfaces/l2tpeth/ipv6/mld/static-group/source/configd_allowed.sh";
					configd:create "/opt/vyatta/share/tmplscripts/interfaces/l2tpeth/ipv6/mld/static-group/source/configd_create.sh";
					configd:delete "/opt/vyatta/share/tmplscripts/interfaces/l2tpeth/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/l2tpeth/ipv6/mld/last-member-query-interval/configd_update.sh";
				configd:delete "/opt/vyatta/share/tmplscripts/interfaces/l2tpeth/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/l2tpeth/ipv6/mld/version/configd_update.sh";
				configd:delete "/opt/vyatta/share/tmplscripts/interfaces/l2tpeth/ipv6/mld/version/configd_delete.sh";
			}
			leaf access-group {
				type string;
				configd:help "Control the multicast local-membership groups learnt on an interface";
				configd:allowed "/opt/vyatta/share/tmplscripts/interfaces/l2tpeth/ipv6/mld/access-group/configd_allowed.sh";
				configd:update "/opt/vyatta/share/tmplscripts/interfaces/l2tpeth/ipv6/mld/access-group/configd_update.sh";
				configd:delete "/opt/vyatta/share/tmplscripts/interfaces/l2tpeth/ipv6/mld/access-group/configd_delete.sh";
				configd:validate "/opt/vyatta/share/tmplscripts/interfaces/l2tpeth/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/l2tpeth/ipv6/mld/query-interval/configd_delete.sh";
				configd:validate "/opt/vyatta/share/tmplscripts/interfaces/l2tpeth/ipv6/mld/query-interval/configd_validate1.cli";
			}
		}
	}
	augment /if:interfaces/interfaces-l2tpeth:l2tpeth/interfaces-l2tpeth:vif/interfaces-l2tpeth:ipv6 {
		container mld {
			presence "true";
			configd:priority "960";
			configd:help "Multicast Listener Discovery (MLD)";
			configd:end "/opt/vyatta/share/tmplscripts/interfaces/l2tpeth/vif/ipv6/mld/configd_end.sh";
			configd:validate "/opt/vyatta/share/tmplscripts/interfaces/l2tpeth/vif/ipv6/mld/configd_validate1.cli";
			configd:validate "/opt/vyatta/share/tmplscripts/interfaces/l2tpeth/vif/ipv6/mld/configd_validate2.cli";
			configd:validate "/opt/vyatta/share/tmplscripts/interfaces/l2tpeth/vif/ipv6/mld/configd_validate3.cli";
			container immediate-leave {
				presence "true";
				configd:help "Immediate leave feature";
				configd:validate "/opt/vyatta/share/tmplscripts/interfaces/l2tpeth/vif/ipv6/mld/immediate-leave/configd_validate1.cli";
				leaf group-list {
					type string;
					configd:help "Define multicast groups in which the immediate leave feature is enabled";
					configd:allowed "/opt/vyatta/share/tmplscripts/interfaces/l2tpeth/vif/ipv6/mld/immediate-leave/group-list/configd_allowed.sh";
					configd:update "/opt/vyatta/share/tmplscripts/interfaces/l2tpeth/vif/ipv6/mld/immediate-leave/group-list/configd_update.sh";
					configd:delete "/opt/vyatta/share/tmplscripts/interfaces/l2tpeth/vif/ipv6/mld/immediate-leave/group-list/configd_delete.sh";
					configd:validate "/opt/vyatta/share/tmplscripts/interfaces/l2tpeth/vif/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/l2tpeth/vif/ipv6/mld/robustness-variable/configd_update.sh";
				configd:delete "/opt/vyatta/share/tmplscripts/interfaces/l2tpeth/vif/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/l2tpeth/vif/ipv6/mld/querier-timeout/configd_update.sh";
				configd:delete "/opt/vyatta/share/tmplscripts/interfaces/l2tpeth/vif/ipv6/mld/querier-timeout/configd_delete.sh";
			}
			leaf limit-exception {
				type string;
				configd:help "Specify access-list that defines multicast groups that are exempted from being subject to configured limit";
				configd:allowed "/opt/vyatta/share/tmplscripts/interfaces/l2tpeth/vif/ipv6/mld/limit-exception/configd_allowed.sh";
				configd:update "/opt/vyatta/share/tmplscripts/interfaces/l2tpeth/vif/ipv6/mld/limit-exception/configd_update.sh";
				configd:delete "/opt/vyatta/share/tmplscripts/interfaces/l2tpeth/vif/ipv6/mld/limit-exception/configd_delete.sh";
				configd:validate "/opt/vyatta/share/tmplscripts/interfaces/l2tpeth/vif/ipv6/mld/limit-exception/configd_validate1.cli";
				configd:validate "/opt/vyatta/share/tmplscripts/interfaces/l2tpeth/vif/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/l2tpeth/vif/ipv6/mld/limit/configd_update.sh";
				configd:delete "/opt/vyatta/share/tmplscripts/interfaces/l2tpeth/vif/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/l2tpeth/vif/ipv6/mld/query-max-response-time/configd_delete.sh";
				configd:validate "/opt/vyatta/share/tmplscripts/interfaces/l2tpeth/vif/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/l2tpeth/vif/ipv6/mld/last-member-query-count/configd_update.sh";
				configd:delete "/opt/vyatta/share/tmplscripts/interfaces/l2tpeth/vif/ipv6/mld/last-member-query-count/configd_delete.sh";
			}
			list static-group {
				configd:help "Set standard IPv6 Multicast group address to be configured as a static group member";
				configd:create "/opt/vyatta/share/tmplscripts/interfaces/l2tpeth/vif/ipv6/mld/static-group/configd_create.sh";
				configd:end "/opt/vyatta/share/tmplscripts/interfaces/l2tpeth/vif/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/l2tpeth/vif/ipv6/mld/static-group/source/configd_syntax1.cli";
					}
					ordered-by "user";
					configd:help "Configure standard IPv6 source address as a static source from where multicast packets originate";
					configd:allowed "/opt/vyatta/share/tmplscripts/interfaces/l2tpeth/vif/ipv6/mld/static-group/source/configd_allowed.sh";
					configd:create "/opt/vyatta/share/tmplscripts/interfaces/l2tpeth/vif/ipv6/mld/static-group/source/configd_create.sh";
					configd:delete "/opt/vyatta/share/tmplscripts/interfaces/l2tpeth/vif/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/l2tpeth/vif/ipv6/mld/last-member-query-interval/configd_update.sh";
				configd:delete "/opt/vyatta/share/tmplscripts/interfaces/l2tpeth/vif/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/l2tpeth/vif/ipv6/mld/version/configd_update.sh";
				configd:delete "/opt/vyatta/share/tmplscripts/interfaces/l2tpeth/vif/ipv6/mld/version/configd_delete.sh";
			}
			leaf access-group {
				type string;
				configd:help "Control the multicast local-membership groups learnt on an interface";
				configd:allowed "/opt/vyatta/share/tmplscripts/interfaces/l2tpeth/vif/ipv6/mld/access-group/configd_allowed.sh";
				configd:update "/opt/vyatta/share/tmplscripts/interfaces/l2tpeth/vif/ipv6/mld/access-group/configd_update.sh";
				configd:delete "/opt/vyatta/share/tmplscripts/interfaces/l2tpeth/vif/ipv6/mld/access-group/configd_delete.sh";
				configd:validate "/opt/vyatta/share/tmplscripts/interfaces/l2tpeth/vif/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/l2tpeth/vif/ipv6/mld/query-interval/configd_delete.sh";
				configd:validate "/opt/vyatta/share/tmplscripts/interfaces/l2tpeth/vif/ipv6/mld/query-interval/configd_validate1.cli";
			}
		}
	}
	augment /if:interfaces/interfaces-loopback:loopback/interfaces-loopback:ipv6 {
		container mld {
			presence "true";
			configd:priority "960";
			configd:help "Multicast Listener Discovery (MLD)";
			configd:end "/opt/vyatta/share/tmplscripts/interfaces/loopback/ipv6/mld/configd_end.sh";
			configd:validate "/opt/vyatta/share/tmplscripts/interfaces/loopback/ipv6/mld/configd_validate1.cli";
			configd:validate "/opt/vyatta/share/tmplscripts/interfaces/loopback/ipv6/mld/configd_validate2.cli";
			configd:validate "/opt/vyatta/share/tmplscripts/interfaces/loopback/ipv6/mld/configd_validate3.cli";
			container immediate-leave {
				presence "true";
				configd:help "Immediate leave feature";
				configd:validate "/opt/vyatta/share/tmplscripts/interfaces/loopback/ipv6/mld/immediate-leave/configd_validate1.cli";
				leaf group-list {
					type string;
					configd:help "Define multicast groups in which the immediate leave feature is enabled";
					configd:allowed "/opt/vyatta/share/tmplscripts/interfaces/loopback/ipv6/mld/immediate-leave/group-list/configd_allowed.sh";
					configd:update "/opt/vyatta/share/tmplscripts/interfaces/loopback/ipv6/mld/immediate-leave/group-list/configd_update.sh";
					configd:delete "/opt/vyatta/share/tmplscripts/interfaces/loopback/ipv6/mld/immediate-leave/group-list/configd_delete.sh";
					configd:validate "/opt/vyatta/share/tmplscripts/interfaces/loopback/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/loopback/ipv6/mld/robustness-variable/configd_update.sh";
				configd:delete "/opt/vyatta/share/tmplscripts/interfaces/loopback/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/loopback/ipv6/mld/querier-timeout/configd_update.sh";
				configd:delete "/opt/vyatta/share/tmplscripts/interfaces/loopback/ipv6/mld/querier-timeout/configd_delete.sh";
			}
			leaf limit-exception {
				type string;
				configd:help "Specify access-list that defines multicast groups that are exempted from being subject to configured limit";
				configd:allowed "/opt/vyatta/share/tmplscripts/interfaces/loopback/ipv6/mld/limit-exception/configd_allowed.sh";
				configd:update "/opt/vyatta/share/tmplscripts/interfaces/loopback/ipv6/mld/limit-exception/configd_update.sh";
				configd:delete "/opt/vyatta/share/tmplscripts/interfaces/loopback/ipv6/mld/limit-exception/configd_delete.sh";
				configd:validate "/opt/vyatta/share/tmplscripts/interfaces/loopback/ipv6/mld/limit-exception/configd_validate1.cli";
				configd:validate "/opt/vyatta/share/tmplscripts/interfaces/loopback/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/loopback/ipv6/mld/limit/configd_update.sh";
				configd:delete "/opt/vyatta/share/tmplscripts/interfaces/loopback/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/loopback/ipv6/mld/query-max-response-time/configd_delete.sh";
				configd:validate "/opt/vyatta/share/tmplscripts/interfaces/loopback/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/loopback/ipv6/mld/last-member-query-count/configd_update.sh";
				configd:delete "/opt/vyatta/share/tmplscripts/interfaces/loopback/ipv6/mld/last-member-query-count/configd_delete.sh";
			}
			list static-group {
				configd:help "Set standard IPv6 Multicast group address to be configured as a static group member";
				configd:create "/opt/vyatta/share/tmplscripts/interfaces/loopback/ipv6/mld/static-group/configd_create.sh";
				configd:end "/opt/vyatta/share/tmplscripts/interfaces/loopback/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/loopback/ipv6/mld/static-group/source/configd_syntax1.cli";
					}
					ordered-by "user";
					configd:help "Configure standard IPv6 source address as a static source from where multicast packets originate";
					configd:allowed "/opt/vyatta/share/tmplscripts/interfaces/loopback/ipv6/mld/static-group/source/configd_allowed.sh";
					configd:create "/opt/vyatta/share/tmplscripts/interfaces/loopback/ipv6/mld/static-group/source/configd_create.sh";
					configd:delete "/opt/vyatta/share/tmplscripts/interfaces/loopback/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/loopback/ipv6/mld/last-member-query-interval/configd_update.sh";
				configd:delete "/opt/vyatta/share/tmplscripts/interfaces/loopback/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/loopback/ipv6/mld/version/configd_update.sh";
				configd:delete "/opt/vyatta/share/tmplscripts/interfaces/loopback/ipv6/mld/version/configd_delete.sh";
			}
			leaf access-group {
				type string;
				configd:help "Control the multicast local-membership groups learnt on an interface";
				configd:allowed "/opt/vyatta/share/tmplscripts/interfaces/loopback/ipv6/mld/access-group/configd_allowed.sh";
				configd:update "/opt/vyatta/share/tmplscripts/interfaces/loopback/ipv6/mld/access-group/configd_update.sh";
				configd:delete "/opt/vyatta/share/tmplscripts/interfaces/loopback/ipv6/mld/access-group/configd_delete.sh";
				configd:validate "/opt/vyatta/share/tmplscripts/interfaces/loopback/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/loopback/ipv6/mld/query-interval/configd_delete.sh";
				configd:validate "/opt/vyatta/share/tmplscripts/interfaces/loopback/ipv6/mld/query-interval/configd_validate1.cli";
			}
		}
	}
	augment /if:interfaces/interfaces-openvpn:openvpn/interfaces-openvpn:ipv6 {
		container mld {
			presence "true";
			configd:priority "960";
			configd:help "Multicast Listener Discovery (MLD)";
			configd:end "/opt/vyatta/share/tmplscripts/interfaces/openvpn/ipv6/mld/configd_end.sh";
			configd:validate "/opt/vyatta/share/tmplscripts/interfaces/openvpn/ipv6/mld/configd_validate1.cli";
			configd:validate "/opt/vyatta/share/tmplscripts/interfaces/openvpn/ipv6/mld/configd_validate2.cli";
			configd:validate "/opt/vyatta/share/tmplscripts/interfaces/openvpn/ipv6/mld/configd_validate3.cli";
			container immediate-leave {
				presence "true";
				configd:help "Immediate leave feature";
				configd:validate "/opt/vyatta/share/tmplscripts/interfaces/openvpn/ipv6/mld/immediate-leave/configd_validate1.cli";
				leaf group-list {
					type string;
					configd:help "Define multicast groups in which the immediate leave feature is enabled";
					configd:allowed "/opt/vyatta/share/tmplscripts/interfaces/openvpn/ipv6/mld/immediate-leave/group-list/configd_allowed.sh";
					configd:update "/opt/vyatta/share/tmplscripts/interfaces/openvpn/ipv6/mld/immediate-leave/group-list/configd_update.sh";
					configd:delete "/opt/vyatta/share/tmplscripts/interfaces/openvpn/ipv6/mld/immediate-leave/group-list/configd_delete.sh";
					configd:validate "/opt/vyatta/share/tmplscripts/interfaces/openvpn/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/openvpn/ipv6/mld/robustness-variable/configd_update.sh";
				configd:delete "/opt/vyatta/share/tmplscripts/interfaces/openvpn/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/openvpn/ipv6/mld/querier-timeout/configd_update.sh";
				configd:delete "/opt/vyatta/share/tmplscripts/interfaces/openvpn/ipv6/mld/querier-timeout/configd_delete.sh";
			}
			leaf limit-exception {
				type string;
				configd:help "Specify access-list that defines multicast groups that are exempted from being subject to configured limit";
				configd:allowed "/opt/vyatta/share/tmplscripts/interfaces/openvpn/ipv6/mld/limit-exception/configd_allowed.sh";
				configd:update "/opt/vyatta/share/tmplscripts/interfaces/openvpn/ipv6/mld/limit-exception/configd_update.sh";
				configd:delete "/opt/vyatta/share/tmplscripts/interfaces/openvpn/ipv6/mld/limit-exception/configd_delete.sh";
				configd:validate "/opt/vyatta/share/tmplscripts/interfaces/openvpn/ipv6/mld/limit-exception/configd_validate1.cli";
				configd:validate "/opt/vyatta/share/tmplscripts/interfaces/openvpn/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/openvpn/ipv6/mld/limit/configd_update.sh";
				configd:delete "/opt/vyatta/share/tmplscripts/interfaces/openvpn/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/openvpn/ipv6/mld/query-max-response-time/configd_delete.sh";
				configd:validate "/opt/vyatta/share/tmplscripts/interfaces/openvpn/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/openvpn/ipv6/mld/last-member-query-count/configd_update.sh";
				configd:delete "/opt/vyatta/share/tmplscripts/interfaces/openvpn/ipv6/mld/last-member-query-count/configd_delete.sh";
			}
			list static-group {
				configd:help "Set standard IPv6 Multicast group address to be configured as a static group member";
				configd:create "/opt/vyatta/share/tmplscripts/interfaces/openvpn/ipv6/mld/static-group/configd_create.sh";
				configd:end "/opt/vyatta/share/tmplscripts/interfaces/openvpn/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/openvpn/ipv6/mld/static-group/source/configd_syntax1.cli";
					}
					ordered-by "user";
					configd:help "Configure standard IPv6 source address as a static source from where multicast packets originate";
					configd:allowed "/opt/vyatta/share/tmplscripts/interfaces/openvpn/ipv6/mld/static-group/source/configd_allowed.sh";
					configd:create "/opt/vyatta/share/tmplscripts/interfaces/openvpn/ipv6/mld/static-group/source/configd_create.sh";
					configd:delete "/opt/vyatta/share/tmplscripts/interfaces/openvpn/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/openvpn/ipv6/mld/last-member-query-interval/configd_update.sh";
				configd:delete "/opt/vyatta/share/tmplscripts/interfaces/openvpn/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/openvpn/ipv6/mld/version/configd_update.sh";
				configd:delete "/opt/vyatta/share/tmplscripts/interfaces/openvpn/ipv6/mld/version/configd_delete.sh";
			}
			leaf access-group {
				type string;
				configd:help "Control the multicast local-membership groups learnt on an interface";
				configd:allowed "/opt/vyatta/share/tmplscripts/interfaces/openvpn/ipv6/mld/access-group/configd_allowed.sh";
				configd:update "/opt/vyatta/share/tmplscripts/interfaces/openvpn/ipv6/mld/access-group/configd_update.sh";
				configd:delete "/opt/vyatta/share/tmplscripts/interfaces/openvpn/ipv6/mld/access-group/configd_delete.sh";
				configd:validate "/opt/vyatta/share/tmplscripts/interfaces/openvpn/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/openvpn/ipv6/mld/query-interval/configd_delete.sh";
				configd:validate "/opt/vyatta/share/tmplscripts/interfaces/openvpn/ipv6/mld/query-interval/configd_validate1.cli";
			}
		}
	}
	augment /if:interfaces/interfaces-tunnel:tunnel/interfaces-tunnel:ipv6 {
		container mld {
			presence "true";
			configd:priority "960";
			configd:help "Multicast Listener Discovery (MLD)";
			configd:end "/opt/vyatta/share/tmplscripts/interfaces/tunnel/ipv6/mld/configd_end.sh";
			configd:validate "/opt/vyatta/share/tmplscripts/interfaces/tunnel/ipv6/mld/configd_validate1.cli";
			configd:validate "/opt/vyatta/share/tmplscripts/interfaces/tunnel/ipv6/mld/configd_validate2.cli";
			configd:validate "/opt/vyatta/share/tmplscripts/interfaces/tunnel/ipv6/mld/configd_validate3.cli";
			container immediate-leave {
				presence "true";
				configd:help "Immediate leave feature";
				configd:validate "/opt/vyatta/share/tmplscripts/interfaces/tunnel/ipv6/mld/immediate-leave/configd_validate1.cli";
				leaf group-list {
					type string;
					configd:help "Define multicast groups in which the immediate leave feature is enabled";
					configd:allowed "/opt/vyatta/share/tmplscripts/interfaces/tunnel/ipv6/mld/immediate-leave/group-list/configd_allowed.sh";
					configd:update "/opt/vyatta/share/tmplscripts/interfaces/tunnel/ipv6/mld/immediate-leave/group-list/configd_update.sh";
					configd:delete "/opt/vyatta/share/tmplscripts/interfaces/tunnel/ipv6/mld/immediate-leave/group-list/configd_delete.sh";
					configd:validate "/opt/vyatta/share/tmplscripts/interfaces/tunnel/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/tunnel/ipv6/mld/robustness-variable/configd_update.sh";
				configd:delete "/opt/vyatta/share/tmplscripts/interfaces/tunnel/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/tunnel/ipv6/mld/querier-timeout/configd_update.sh";
				configd:delete "/opt/vyatta/share/tmplscripts/interfaces/tunnel/ipv6/mld/querier-timeout/configd_delete.sh";
			}
			leaf limit-exception {
				type string;
				configd:help "Specify access-list that defines multicast groups that are exempted from being subject to configured limit";
				configd:allowed "/opt/vyatta/share/tmplscripts/interfaces/tunnel/ipv6/mld/limit-exception/configd_allowed.sh";
				configd:update "/opt/vyatta/share/tmplscripts/interfaces/tunnel/ipv6/mld/limit-exception/configd_update.sh";
				configd:delete "/opt/vyatta/share/tmplscripts/interfaces/tunnel/ipv6/mld/limit-exception/configd_delete.sh";
				configd:validate "/opt/vyatta/share/tmplscripts/interfaces/tunnel/ipv6/mld/limit-exception/configd_validate1.cli";
				configd:validate "/opt/vyatta/share/tmplscripts/interfaces/tunnel/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/tunnel/ipv6/mld/limit/configd_update.sh";
				configd:delete "/opt/vyatta/share/tmplscripts/interfaces/tunnel/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/tunnel/ipv6/mld/query-max-response-time/configd_delete.sh";
				configd:validate "/opt/vyatta/share/tmplscripts/interfaces/tunnel/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/tunnel/ipv6/mld/last-member-query-count/configd_update.sh";
				configd:delete "/opt/vyatta/share/tmplscripts/interfaces/tunnel/ipv6/mld/last-member-query-count/configd_delete.sh";
			}
			list static-group {
				configd:help "Set standard IPv6 Multicast group address to be configured as a static group member";
				configd:create "/opt/vyatta/share/tmplscripts/interfaces/tunnel/ipv6/mld/static-group/configd_create.sh";
				configd:end "/opt/vyatta/share/tmplscripts/interfaces/tunnel/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/tunnel/ipv6/mld/static-group/source/configd_syntax1.cli";
					}
					ordered-by "user";
					configd:help "Configure standard IPv6 source address as a static source from where multicast packets originate";
					configd:allowed "/opt/vyatta/share/tmplscripts/interfaces/tunnel/ipv6/mld/static-group/source/configd_allowed.sh";
					configd:create "/opt/vyatta/share/tmplscripts/interfaces/tunnel/ipv6/mld/static-group/source/configd_create.sh";
					configd:delete "/opt/vyatta/share/tmplscripts/interfaces/tunnel/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/tunnel/ipv6/mld/last-member-query-interval/configd_update.sh";
				configd:delete "/opt/vyatta/share/tmplscripts/interfaces/tunnel/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/tunnel/ipv6/mld/version/configd_update.sh";
				configd:delete "/opt/vyatta/share/tmplscripts/interfaces/tunnel/ipv6/mld/version/configd_delete.sh";
			}
			leaf access-group {
				type string;
				configd:help "Control the multicast local-membership groups learnt on an interface";
				configd:allowed "/opt/vyatta/share/tmplscripts/interfaces/tunnel/ipv6/mld/access-group/configd_allowed.sh";
				configd:update "/opt/vyatta/share/tmplscripts/interfaces/tunnel/ipv6/mld/access-group/configd_update.sh";
				configd:delete "/opt/vyatta/share/tmplscripts/interfaces/tunnel/ipv6/mld/access-group/configd_delete.sh";
				configd:validate "/opt/vyatta/share/tmplscripts/interfaces/tunnel/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/tunnel/ipv6/mld/query-interval/configd_delete.sh";
				configd:validate "/opt/vyatta/share/tmplscripts/interfaces/tunnel/ipv6/mld/query-interval/configd_validate1.cli";
			}
		}
	}
	augment /if:interfaces/interfaces-vti:vti/interfaces-vti:ipv6 {
		container mld {
			presence "true";
			configd:priority "960";
			configd:help "Multicast Listener Discovery (MLD)";
			configd:end "/opt/vyatta/share/tmplscripts/interfaces/vti/ipv6/mld/configd_end.sh";
			configd:validate "/opt/vyatta/share/tmplscripts/interfaces/vti/ipv6/mld/configd_validate1.cli";
			configd:validate "/opt/vyatta/share/tmplscripts/interfaces/vti/ipv6/mld/configd_validate2.cli";
			configd:validate "/opt/vyatta/share/tmplscripts/interfaces/vti/ipv6/mld/configd_validate3.cli";
			container immediate-leave {
				presence "true";
				configd:help "Immediate leave feature";
				configd:validate "/opt/vyatta/share/tmplscripts/interfaces/vti/ipv6/mld/immediate-leave/configd_validate1.cli";
				leaf group-list {
					type string;
					configd:help "Define multicast groups in which the immediate leave feature is enabled";
					configd:allowed "/opt/vyatta/share/tmplscripts/interfaces/vti/ipv6/mld/immediate-leave/group-list/configd_allowed.sh";
					configd:update "/opt/vyatta/share/tmplscripts/interfaces/vti/ipv6/mld/immediate-leave/group-list/configd_update.sh";
					configd:delete "/opt/vyatta/share/tmplscripts/interfaces/vti/ipv6/mld/immediate-leave/group-list/configd_delete.sh";
					configd:validate "/opt/vyatta/share/tmplscripts/interfaces/vti/ipv6/mld/immediate-leave/group-list/configd_validate1.cli";
				}
			}
			leaf robustness-variable {
				type uint32 {
					range 2..7 {
						error-message "Must be between 2-7";
					}
				}
				configd:help "Configure the robustness variable value on an interface";
				configd:update "/opt/vyatta/share/tmplscripts/interfaces/vti/ipv6/mld/robustness-variable/configd_update.sh";
				configd:delete "/opt/vyatta/share/tmplscripts/interfaces/vti/ipv6/mld/robustness-variable/configd_delete.sh";
			}
			leaf querier-timeout {
				type uint32 {
					range 60..300 {
						error-message "Must be between 60-300";
					}
				}
				configd:help "Configure the timeout period that the router waits after the previous querier has stopped querying before it takes over as the querier";
				configd:update "/opt/vyatta/share/tmplscripts/interfaces/vti/ipv6/mld/querier-timeout/configd_update.sh";
				configd:delete "/opt/vyatta/share/tmplscripts/interfaces/vti/ipv6/mld/querier-timeout/configd_delete.sh";
			}
			leaf limit-exception {
				type string;
				configd:help "Specify access-list that defines multicast groups that are exempted from being subject to configured limit";
				configd:allowed "/opt/vyatta/share/tmplscripts/interfaces/vti/ipv6/mld/limit-exception/configd_allowed.sh";
				configd:update "/opt/vyatta/share/tmplscripts/interfaces/vti/ipv6/mld/limit-exception/configd_update.sh";
				configd:delete "/opt/vyatta/share/tmplscripts/interfaces/vti/ipv6/mld/limit-exception/configd_delete.sh";
				configd:validate "/opt/vyatta/share/tmplscripts/interfaces/vti/ipv6/mld/limit-exception/configd_validate1.cli";
				configd:validate "/opt/vyatta/share/tmplscripts/interfaces/vti/ipv6/mld/limit-exception/configd_validate2.cli";
			}
			leaf limit {
				type uint32 {
					range 1..2097152 {
						error-message "Must be between 1-2097152";
					}
				}
				configd:help "Configure the limit on the maximum number of group membership states";
				configd:update "/opt/vyatta/share/tmplscripts/interfaces/vti/ipv6/mld/limit/configd_update.sh";
				configd:delete "/opt/vyatta/share/tmplscripts/interfaces/vti/ipv6/mld/limit/configd_delete.sh";
			}
			leaf query-max-response-time {
				type uint32 {
					range 1..240 {
						error-message "Must be between 1-240";
					}
				}
				configd:help "Configure the maximum response time advertised in MLD queries";
				configd:delete "/opt/vyatta/share/tmplscripts/interfaces/vti/ipv6/mld/query-max-response-time/configd_delete.sh";
				configd:validate "/opt/vyatta/share/tmplscripts/interfaces/vti/ipv6/mld/query-max-response-time/configd_validate1.cli";
			}
			leaf last-member-query-count {
				type uint32 {
					range 2..7 {
						error-message "Must be between 2-7";
					}
				}
				configd:help "Set the last-member query-count value";
				configd:update "/opt/vyatta/share/tmplscripts/interfaces/vti/ipv6/mld/last-member-query-count/configd_update.sh";
				configd:delete "/opt/vyatta/share/tmplscripts/interfaces/vti/ipv6/mld/last-member-query-count/configd_delete.sh";
			}
			list static-group {
				configd:help "Set standard IPv6 Multicast group address to be configured as a static group member";
				configd:create "/opt/vyatta/share/tmplscripts/interfaces/vti/ipv6/mld/static-group/configd_create.sh";
				configd:end "/opt/vyatta/share/tmplscripts/interfaces/vti/ipv6/mld/static-group/configd_end.sh";
				key "tagnode";
				leaf tagnode {
					type types:ipv6-address;
					configd:help "Set standard IPv6 Multicast group address to be configured as a static group member";
				}
				leaf-list source {
					type string {
						configd:syntax "/opt/vyatta/share/tmplscripts/interfaces/vti/ipv6/mld/static-group/source/configd_syntax1.cli";
					}
					ordered-by "user";
					configd:help "Configure standard IPv6 source address as a static source from where multicast packets originate";
					configd:allowed "/opt/vyatta/share/tmplscripts/interfaces/vti/ipv6/mld/static-group/source/configd_allowed.sh";
					configd:create "/opt/vyatta/share/tmplscripts/interfaces/vti/ipv6/mld/static-group/source/configd_create.sh";
					configd:delete "/opt/vyatta/share/tmplscripts/interfaces/vti/ipv6/mld/static-group/source/configd_delete.sh";
				}
			}
			leaf last-member-query-interval {
				type uint32 {
					range 1000..25500 {
						error-message "Must be between 1000-25500";
					}
				}
				configd:help "Configure the frequency at which the router sends MLD group-specific host query messages";
				configd:update "/opt/vyatta/share/tmplscripts/interfaces/vti/ipv6/mld/last-member-query-interval/configd_update.sh";
				configd:delete "/opt/vyatta/share/tmplscripts/interfaces/vti/ipv6/mld/last-member-query-interval/configd_delete.sh";
			}
			leaf version {
				type uint32 {
					range 1..2 {
						error-message "Must be between 1-2";
					}
				}
				configd:help "Configure the current MLD protocol version on an interface";
				configd:update "/opt/vyatta/share/tmplscripts/interfaces/vti/ipv6/mld/version/configd_update.sh";
				configd:delete "/opt/vyatta/share/tmplscripts/interfaces/vti/ipv6/mld/version/configd_delete.sh";
			}
			leaf access-group {
				type string;
				configd:help "Control the multicast local-membership groups learnt on an interface";
				configd:allowed "/opt/vyatta/share/tmplscripts/interfaces/vti/ipv6/mld/access-group/configd_allowed.sh";
				configd:update "/opt/vyatta/share/tmplscripts/interfaces/vti/ipv6/mld/access-group/configd_update.sh";
				configd:delete "/opt/vyatta/share/tmplscripts/interfaces/vti/ipv6/mld/access-group/configd_delete.sh";
				configd:validate "/opt/vyatta/share/tmplscripts/interfaces/vti/ipv6/mld/access-group/configd_validate1.cli";
			}
			leaf query-interval {
				type uint32 {
					range 1..18000 {
						error-message "Must be between 1-18000";
					}
				}
				configd:help "Configure the frequency of sending MLD host query messages";
				configd:delete "/opt/vyatta/share/tmplscripts/interfaces/vti/ipv6/mld/query-interval/configd_delete.sh";
				configd:validate "/opt/vyatta/share/tmplscripts/interfaces/vti/ipv6/mld/query-interval/configd_validate1.cli";
			}
		}
	}
}
