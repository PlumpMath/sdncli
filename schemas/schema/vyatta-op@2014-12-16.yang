module vyatta-op {
	namespace "urn:vyatta.com:mgmt:vyatta-op";
	prefix vyatta-op;

	import vyatta-types {
		prefix types;
	}
	import configd {
		prefix configd;
	}

	description "Supported RPC calls.
		     Do not add anything to this file.";
	organization "Brocade Communications Systems, Inc.";
	contact	"Brocade Communications Systems, Inc.
		 Postal: 130 Holger Way
		         San Jose, CA 95134
		 E-mail: support@Brocade.com
		 Web: www.brocade.com";

	revision 2014-12-16 {
		description "Initial revision.";
	}

	rpc ping {
		description "Generates Ping and return response";
		input {
			leaf host {
				type string;
				mandatory true;
			}
			leaf count {
				type uint32;
				default 3;
				description "Number of ping echo request message to send";
			}
			leaf ttl {
				type uint8;
				default "255";
				description "IP Time To Live";
			}
		}
		output {
			leaf tx-packet-count {
				type uint32;
				description "Transmitted Packet count";
			}
			leaf rx-packet-count {
				type uint32;
				description "Received packet count";
			}
			leaf min-delay {
				type uint32;
				units "milliseconds";
				description "Minimum packet delay";
			}
			leaf average-delay {
				type uint32;
				units "milliseconds";
				description "Average packet delay";
			}
			leaf max-delay {
				type uint32;
				units "millisecond";
				description "Minimum packet delay";
			}
		}
		configd:rpc-script "/opt/vyatta/bin/yangop-ping.pl";
	}
	rpc interface {
		input {
			leaf name {
				type string;
				mandatory true;
				description "Interface name to query";
			}
		}
		output {
			list address {
				key ip;
				leaf ip {
					type types:ip-prefix;
					description "Interface IP address";
				}
			}
			leaf admin-status {
				type enumeration {
					enum up;
					enum down;
					enum testing;
				}
				description "Interface's desired state";
			}
			leaf oper-status {
				type enumeration {
					enum up;
					enum down;
					enum testing;
					enum unknown;
					enum dormant;
					enum notpresent;
					enum lowerlayerdown;
				}
				description "Interface's current operational state";
			}
			leaf description {
				type string;
				description "Interface description";
			}
		}
		configd:rpc-script "/opt/vyatta/bin/yangop-interface.pl";
	}
	rpc route {
		typedef destination {
			type union {
				type types:ip-address;
				type types:ip-prefix;
			}
		}
		input {
			leaf family {
				type enumeration {
					enum ipv4;
					enum ipv6;
				}
				default ipv4;
			}
			leaf destination {
				type destination;
				description "Destination host or network";
			}
		}
		output {
			list route {
				key destination;
				leaf destination {
					type destination;
					description "Destination";
				}
				leaf source {
					type types:ip-address;
					description "Source address";
				}
				list path {
					key entry;
					leaf entry {
						type uint64;
					}
					leaf device {
						type string;
						description "Device name";
					}
					leaf next-hop {
						type types:ip-address;
						description "Next-hop";
					}
				}
			}
		}
		configd:rpc-script "/opt/vyatta/bin/yangop-route.pl";
	}
}
