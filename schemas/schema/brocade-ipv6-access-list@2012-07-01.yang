/***********************************************************************
 * brocade-ipv6-access.yang: Brocade IP Forwarding data model.
 *
 * March  2011, Bhavin Patel
 *
 * Copyright (c) 2011 by Brocade Communications Systems, Inc.
 * All rights reserved.
 *
 **********************************************************************/
module brocade-ipv6-access-list {
    namespace "urn:brocade.com:mgmt:brocade-ipv6-access-list";
    prefix ipv6-access-list;
    import brocade-rbridge { prefix rbridge; }
    import brocade-interface { prefix interface; }
    import tailf-common {
        prefix tailf;
    }

    import brocade-ipv6-config {
        prefix ipv6-config;
    }

    import ietf-inet-types {
        prefix "inet";
    }

	import brocade-ip-access-list { prefix "ip-access-list"; }

    organization
        "Brocade Communications Systems, Inc.";

    contact
        "Brocade Communications Systems, Inc.
        Postal: 130 Holger Way
                San Jose, CA 95134
                U.S.A
        Tel: +1-408-333-8000
        E-mail: support@Brocade.com
        Web: www.brocade.com";

    description
        "This management sub-module contains the configuration
        and rpc implementaion for IP Access-list.";

    revision "2012-07-01" {
       description "Initial version";
    }

    typedef sip {
        type inet:ipv6-address;
    }

    typedef sip-cidr {
        type inet:ipv6-prefix;
    }

    typedef dip {
        type inet:ipv6-address;
    }

    typedef dip-cidr {
        type inet:ipv6-prefix;
    }

    typedef dip-mask {
        type inet:ipv6-address;
    }    

    typedef sip-mask {
        type inet:ipv6-address;
    }

    typedef ipv6-l3-acl-policy-name {
        type string {
            pattern '[a-zA-Z0-9]{1}([-a-zA-Z0-9_]{0,62})' {
            }
            length 1..63;
        }
    }

    grouping ipv6-ext-access-list-rule {
        leaf action {
            type enumeration {
                enum permit {
                    value 1;
                }
                enum deny {
                    value 2;
                }

                enum hard-drop {
                    value 3;
                }

            }
            mandatory true;
        }

        leaf protocol-type {
            type union {
                type enumeration {
                    enum tcp {
                        value 6;
                    }
                    enum udp {
                        value 17;
                    }
                    enum ipv6 {
                        value 41;
                    }
                    enum ipv6-icmp {
                        value 58;
                    }
                }
                type ip-access-list:proto-type;
            }
            mandatory true;
        }

            
        leaf src-host-any-sip {
            type union {
                type enumeration {
                    enum any {
                        value 1;
                    }
                    enum host {
                        value 2;
                    }
                }
//                type sip;
                type sip-cidr;
            }
            mandatory true;
        }

        leaf src-host-ip {
            when "../src-host-any-sip ='host'" {
            }
            type sip;
        }

        leaf src-mask {
            when "((../src-host-any-sip !='any') and 
                (../src-host-any-sip !='host') and 
                ((not(contains((../src-host-any-sip),'/')))))" {
            }
            type sip-mask;
        }

        leaf sport {
               when "((../protocol-type ='tcp') or 
                (../protocol-type ='udp') or 
                (../protocol-type ='6') or 
                (../protocol-type ='17'))" {
            }
            type enumeration {
                enum eq {
                    value 1;
                }
                enum gt {
                    value 2;
                } 
                enum lt {
                    value 3;
                }
                enum neq {
                    value 4;
                }
                enum range {
                    value 5;
                }
            } // type enumeration
        } //type sport
        
        leaf sport-number-eq-neq-tcp {
            when "(((../protocol-type ='tcp') or 
                (../protocol-type ='6')) and 
                ((../sport ='eq') or
                (../sport ='neq')))" {
            }
            type union {
                type ip-access-list:wellknown-port-tcp;            
                type ip-access-list:sport-number-eq-neq-tcp-udp;
            }
        }
        
        leaf sport-number-lt-tcp {
            when "(((../protocol-type ='tcp') or 
                (../protocol-type ='6')) and 
                (../sport ='lt'))" {
            }
            type union {
                type ip-access-list:wellknown-port-tcp;            
                type ip-access-list:sport-number-lt-tcp-udp;
            }
        }
        
        leaf sport-number-gt-tcp {
            when "(((../protocol-type ='tcp') or
                (../protocol-type ='6')) and 
                (../sport ='gt'))" {
            }
            type union {
                type ip-access-list:wellknown-port-tcp;            
                type ip-access-list:sport-number-gt-tcp-udp;
            }
        }
        
        leaf sport-number-eq-neq-udp {
            when "(((../protocol-type ='udp')
                or (../protocol-type ='17')) 
                and ((../sport ='eq') or 
                (../sport ='neq')))" {
            }
            type union {
                type ip-access-list:wellknown-port-udp;
                type ip-access-list:sport-number-eq-neq-tcp-udp;
            }
        }
        
        leaf sport-number-lt-udp {
            when "(((../protocol-type ='udp') 
                or (../protocol-type ='17')) 
                and (../sport ='lt'))" {
            }
            type union {
                type ip-access-list:wellknown-port-udp;
                type ip-access-list:sport-number-lt-tcp-udp;
            }
        }
        
        leaf sport-number-gt-udp {
            when "(((../protocol-type ='udp') 
                or (../protocol-type ='17')) 
                and (../sport ='gt'))" {
            }
            type union {
                type ip-access-list:wellknown-port-udp;
                type ip-access-list:sport-number-gt-tcp-udp;
            }
        }

        leaf sport-number-range-lower-tcp {
            when "(((../protocol-type ='tcp') 
                or (../protocol-type ='6')) 
                and (../sport ='range'))" {
            }
            type union {    
                type ip-access-list:wellknown-port-tcp;
                type ip-access-list:sport-range-lower-tcp-udp;
            }
        }
    
        leaf sport-number-range-lower-udp {
            when "(((../protocol-type ='udp') 
                or (../protocol-type ='17')) 
                and (../sport ='range'))" {
            }
            type union {
                type ip-access-list:wellknown-port-udp;                            
                type ip-access-list:sport-range-lower-tcp-udp;
            }
        }
       
        leaf sport-number-range-higher-tcp {
            when "(((../protocol-type ='tcp') 
                or (../protocol-type ='6')) 
                and (../sport ='range') 
                and (../sport-number-range-lower-tcp))" {
            }
            type union {            
                type ip-access-list:wellknown-port-tcp;
                type ip-access-list:sport-range-higher-tcp-udp;
            }
        }

        leaf sport-number-range-higher-udp {
            when "(((../protocol-type ='udp') 
                or (../protocol-type ='17')) 
                and (../sport ='range') 
                and (../sport-number-range-lower-udp))" {
            }
            type union {
                type ip-access-list:wellknown-port-udp;
                type ip-access-list:sport-range-higher-tcp-udp;
            }
        }
        
        leaf dst-host-any-dip {
            type union {
                type enumeration {
                    enum any {
                        value 1;
                    }
                    enum host {
                        value 2;
                    }
                }
//                type dip;
                type dip-cidr;
            }
            mandatory true;
        }
    
        leaf dst-host-ip {
            when "../dst-host-any-dip ='host'" {
            }
            type dip;
        }

        leaf dst-mask {
            when "((../dst-host-any-dip !='any') 
                and (../dst-host-any-dip !='host') 
                and ((not(contains((../dst-host-any-dip),'/')))))" {
            }
            type dip-mask;
        }

        leaf dport {
            when "((../protocol-type ='tcp') 
                or (../protocol-type ='17')
                or (../protocol-type ='udp') 
                or (../protocol-type ='6'))" {
            }

            type enumeration {
                enum eq {
                    value 1;
                }
                enum gt {
                    value 2;
                }               
                enum lt {
                    value 3;
                }                
                enum neq {
                    value 4;
                }              
                enum range {
                    value 5;
                }    
            }
        }
        
        leaf dport-number-eq-neq-tcp {
            when "(((../protocol-type ='tcp') 
                or (../protocol-type ='6')) 
                and ((../dport ='eq') 
                or (../dport ='neq')))" {
            }
            type union {
                type ip-access-list:wellknown-port-tcp;            
                type ip-access-list:dport-number-eq-neq-tcp-udp;
            }
        }
    
        leaf dport-number-lt-tcp {
            when "(((../protocol-type ='tcp') 
                or (../protocol-type ='6')) 
                and (../dport ='lt'))" {
            }
            type union {
                type ip-access-list:wellknown-port-tcp;            
                type ip-access-list:dport-number-lt-tcp-udp;
            }
        }
        
        leaf dport-number-gt-tcp {
            when "(((../protocol-type ='tcp') 
                or (../protocol-type ='6')) 
                and (../dport ='gt'))" {
            }
            type union {
                type ip-access-list:wellknown-port-tcp;            
                type ip-access-list:dport-number-gt-tcp-udp;
            }
        }
        
        leaf dport-number-eq-neq-udp {
            when "(((../protocol-type ='udp') 
                or (../protocol-type ='17')) 
                and ((../dport ='eq') 
                or (../dport ='neq')))" {
            }
            type union {
                type ip-access-list:wellknown-port-udp;
                type ip-access-list:dport-number-eq-neq-tcp-udp;
            }
        }
        
        leaf dport-number-lt-udp {
            when "(((../protocol-type ='udp') 
                or (../protocol-type ='17')) 
                and (../dport ='lt'))" {
            }
            type union {
                type ip-access-list:wellknown-port-udp;
                type ip-access-list:dport-number-lt-tcp-udp;
            }
        }

        leaf dport-number-gt-udp {
            when "(((../protocol-type ='udp') 
                or (../protocol-type ='17')) 
                and (../dport ='gt'))" {
            }
            type union {
                type ip-access-list:wellknown-port-udp;
                type ip-access-list:dport-number-gt-tcp-udp;
            }
        }

        leaf dport-number-range-lower-tcp {
            when "(((../protocol-type ='tcp')
                or (../protocol-type ='6'))
                and ((../dport ='range')))" {
            }
            type union {    
                type ip-access-list:wellknown-port-tcp;
                type ip-access-list:dport-range-lower-tcp-udp;
            }
        }

        leaf dport-number-range-lower-udp {
            when "(((../protocol-type ='udp') 
                or (../protocol-type ='17')) 
                and ((../dport ='range')))" {
            }
            type union {
                type ip-access-list:wellknown-port-udp;
                type ip-access-list:dport-range-lower-tcp-udp;
            }
        }
            
        leaf dport-number-range-higher-tcp {
            when "(((../protocol-type ='tcp') or 
                (../protocol-type ='6')) and 
                (../dport ='range') and 
                (../dport-number-range-lower-tcp))" {
            }
            type union {
                type ip-access-list:wellknown-port-tcp;
                type ip-access-list:dport-range-higher-tcp-udp;
            }
        }

        leaf dport-number-range-higher-udp {
            when "(((../protocol-type ='udp') or 
                (../protocol-type ='17')) and 
                (../dport ='range') and 
                (../dport-number-range-lower-udp))" {
            }    
            type union {
                type ip-access-list:wellknown-port-udp;
                type ip-access-list:dport-range-lower-tcp-udp;
            }
        }
        
        leaf dscp {
            type union {
                type ip-access-list:wellknown-dscp;
                type ip-access-list:dscp-uint;
            }
        }

        leaf urg {
            when "(../protocol-type ='tcp') or 
                (../protocol-type ='6')" {
            }
            type empty;
        }
        leaf ack {
            when "(../protocol-type ='tcp') or
                (../protocol-type ='6')" {
            }
            type empty;
        }

        leaf push {
            when "(../protocol-type ='tcp') or
                (../protocol-type ='6')" {
            }
            type empty;
        }

        leaf fin {
            when "(../protocol-type ='tcp') or 
                (../protocol-type ='6')" {
            }
            type empty;
        }


        leaf rst {
            when "(../protocol-type ='tcp') or
                (../protocol-type ='6')" {
            }
            type empty;
        }
        
        leaf sync {
            when "(../protocol-type ='tcp') or
                (../protocol-type ='6')" {
            }
            type empty;
        }
        
        leaf vlan {
            //tailf:alt-name vlan;
            description "Vlan";
            type interface:vlan-type;
        }
        
        leaf count {
            type empty;
        }

        leaf log {
            type empty;
        }

    }

    grouping ipv6-std-access-list-rule {
        leaf action {
            type enumeration {
                enum permit {
                    value 1;
                }
                enum deny {
                    value 2;
                }
                enum hard-drop {
                    value 3;
                }
            }
            mandatory true;
        }
        
        leaf src-host-any-sip {
            type union {
                type enumeration {
                    enum any {
                        value 1;
                    }
                    enum host {
                        value 2;
                    }

                }
//                type sip;
                type sip-cidr; 
            }
            mandatory true;
        }

        leaf src-host-ip {
            when "../src-host-any-sip ='host'" {
            }
            type sip;
        }

        leaf src-mask {
            when "((../src-host-any-sip !='any') and
                (../src-host-any-sip !='host') and
                ((not(contains((../src-host-any-sip),'/')))))" {
            }
            type sip-mask;
        }

        leaf count  {
            type empty;
        }


        leaf log {
            type empty;
        }
        
    }


    grouping ipv6_l3_access_list_cmds {
        container access-list {
            //standard ACL
            list standard {
                key name;
                leaf name {
                    type ipv6-l3-acl-policy-name;
                }
                list seq {
                    key seq-id;
                    leaf seq-id {
                        type ip-access-list:seq-id-std-ext;
                    }
                    uses ipv6-std-access-list-rule;
                }
            }
            //extended ACL
            list extended {
                key name;
                leaf name {
                    type ipv6-l3-acl-policy-name;
                }
                list seq {
                    key seq-id;
                    leaf seq-id {
                        type ip-access-list:seq-id-std-ext;
                    }
                    uses ipv6-ext-access-list-rule;
                }
            } //list extended
        } // container access-list
    }// grouping ip


    grouping ipv6_l3_access_group {
        list access-group {

            key "ipv6-access-list ip-direction";

            leaf ipv6-access-list {
                type ipv6-l3-acl-policy-name;
            }

            leaf ip-direction {
                type enumeration {
                    enum in {
                        value 1;
                    }
                    enum out {
                        value 2;
                    }
                }
            }

            leaf traffic-type {
                type enumeration {
                    enum switched {
                        value 2;
                    }
                    enum routed {
                        value 3;
                    }
                }
            }
        }
    }

    container ipv6-acl{
        container ipv6 {
            uses ipv6_l3_access_list_cmds;
        }
    }

    augment "/interface:interface/interface:tengigabitethernet/interface:ipv6" {
        uses ipv6_l3_access_group {
            refine "access-group" {
            }
        }
    }

    augment "/interface:interface/interface:gigabitethernet/interface:ipv6" {
        uses ipv6_l3_access_group {
            refine "access-group" {
            }
        }
    }

    augment "/interface:interface/interface:fortygigabitethernet/interface:ipv6" {
        uses ipv6_l3_access_group {
            refine "access-group" {
            }
        }
    }

    augment "/interface:interface/interface:hundredgigabitethernet/interface:ipv6" {
        uses ipv6_l3_access_group {
            refine "access-group" {
            }
        }
    }

    augment "/interface:interface/interface:port-channel/interface:ipv6" {
        uses ipv6_l3_access_group {
            refine "access-group" {
            }
        }
    }

/*
    augment "/interface:interface/interface:tengigabitethernet" {
        container ip-acl-interface {
            container ipv6 {
                uses ipv6_l3_access_group;
            }
        }
    }
 
    augment "/interface:interface/interface:gigabitethernet" {
        container ip-acl-interface {
            container ipv6 {
                uses ipv6_l3_access_group;
            }
        }
    }
    
    augment "/interface:interface/interface:fortygigabitethernet" {
        container ip-acl-interface {
            container ipv6 {
                uses ipv6_l3_access_group;
            }
        }
    }
    augment "/interface:interface/interface:hundredgigabitethernet" {
        container ip-acl-interface {
            container ipv6 {
                uses ipv6_l3_access_group;
            }
        }
    }
    

    
    augment "/interface:interface/interface:port-channel" {
        container ip-acl-interface {
            container ipv6 {
                uses ipv6_l3_access_group;
            }
        }
    }
*/


     augment /rbridge:rbridge-id/interface:interface/interface:ve/ipv6-config:ipv6{
        uses ipv6_l3_access_group {
            refine "access-group" {
            }
        }
    }

    /*augment "/interface:interface-vlan/interface:interface/interface:ve" {
        container ip-acl-interface {
            container ipv6 {
                uses ipv6_l3_access_group;
            }
        }
    }*/

	augment "/interface:interface/interface:management/interface:ipv6" {
        container access-group {

            leaf mgmt-ipv6-access-list {
                type ipv6-l3-acl-policy-name;
            }

            leaf mgmt-ip-direction {
                type enumeration {
                    enum in {
                        value 1;
                    }
                }
            }
        }
	}
}
