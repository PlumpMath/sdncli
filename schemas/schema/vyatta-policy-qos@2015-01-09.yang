module vyatta-policy-qos {
	namespace "urn:vyatta.com:mgmt:vyatta-policy-qos";
	prefix policy-qos;

	import vyatta-interfaces {
		prefix if;
	}
	import vyatta-interfaces-dataplane {
		prefix interfaces-dataplane;
	}
	import vyatta-policy {
		prefix policy;
	}
	import vyatta-dscp {
		prefix dscp;
	}
	import vyatta-types {
		prefix types;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2015-01-09 {
		description "Add dscp symbolic names";
	}

	revision 2014-12-04 {
		description "Update for 3.2.1R3";
	}

	revision 2014-11-07 {
		description "Update for 3.2.1R2";
	}
	
	revision 2014-10-28 {
		description "Update for 3.2.1R1";
	}
	
	revision 2014-08-27 {
		description "Initial revision.";
		configd:migration 1;
	}

	typedef name {
		type string {
			pattern "[0-9A-Za-z][-_0-9A-Za-z]*" {
				error-message "Only alpha-numeric name allowed";
			}
			configd:pattern-help "<name>";
		}
	}

	typedef bandwidth-suffix {
		type string {	/* Number followed by suffix */
			pattern '[0-9]+(\.([0-9]+))?(([KMBGTkmgt][iI]?)?(bit|bps))?';
			configd:pattern-help "<number><suffix>";
		}
	}

	typedef bandwidth-percent {
		type string {	/* Number from 1 - 100 follwed by percent */
			pattern '(100|[1-9][0-9]?(\.[0-9]*)?)%';
			configd:pattern-help "<number>%";
		}
	}

	typedef burst-size {
		type uint32 {
			/* Arbitrary maximum: 312500000 is 100ms at 25 Mbits/sec */
			range 1..312500000;
		}
	}

	typedef dscp-name {
		type string {
			configd:syntax "qos-policy.pl --dscp $VAR(@)";
			configd:allowed "qos-policy.pl --allowed-dscp";
			configd:help "DSCP value, name or range";
		}
	}

	grouping marking {
		container mark {
			configd:help "Packet marking action";
			leaf pcp {
				type uint32 {
					range 0..7;
				}
				configd:help "802.1 priority code point to apply";
			}
			leaf dscp {
				type dscp:dscp-name-or-value;
				configd:help "DSCP value to be marked";
			}
		}
	}

	grouping match-rule {
		container tcp {
			presence "true";
			configd:help "TCP flags to match";
			configd:validate "/opt/vyatta/share/tmplscripts/policy/qos/shaper/class/match/tcp/configd_validate1.cli";
			leaf flags {
				type string {
					pattern "(((!?(SYN|ACK|FIN|RST|PSH|URG),)*(!?(SYN|ACK|FIN|RST|PSH|URG))))" {
						error-message "Invalid value for TCP flags. Allowed values : SYN ACK FIN RST URG PSH
When specifying more than one flag, flags should be comma-separated.
For example : value of 'SYN,!ACK,!FIN,!RST' will only match packets with
the SYN flag set, and the ACK, FIN and RST flags unset";
					}
					configd:pattern-help "<TCP-flags>";
				}
				configd:help "TCP flags to match";
				configd:comp_help "/opt/vyatta/share/tmplscripts/security/firewall/name/rule/tcp/flags/configd_comp_help.txt";
			}
		}
		leaf description {
			type string;
			configd:help "Description for this match rule";
		}
		leaf action {
			type enumeration {
				enum "pass";
				enum "drop";
			}
			configd:help "Rule action";
			default "pass";
		}
		leaf pcp {
			type uint32 {
				range 0..7;
			}
			configd:help "802.1 priority code point to match (0 to 7)";
		}

		uses marking;

		container police {
			configd:help "Packet rate limiting";
			configd:validate "/opt/vyatta/share/tmplscripts/security/firewall/name/rule/police/configd_validate.cli";
			leaf bandwidth {
				type bandwidth-suffix;
				configd:help "Bandwidth limit";
			}
			leaf burst {
				type burst-size;
				configd:help "Burst size in bytes";
			}
			container then {
				configd:help "Result for packets over police limit";
				leaf action {
					type enumeration {
						enum "pass";
						enum "drop";
					}
					configd:help "Rule action";
				}
				uses marking;
			}
		}
		leaf fragment {
			type empty;
			configd:help "Match on fragmented packets";
		}
		container source {
			presence "true";
			configd:help "Source parameters";
			leaf mac-address {
				type types:mac-address;
				configd:help "Source MAC address";
				configd:validate "/opt/vyatta/share/tmplscripts/policy/qos/shaper/class/match/source/mac-address/configd_validate1.cli";
				configd:validate "/opt/vyatta/share/tmplscripts/policy/qos/shaper/class/match/source/mac-address/configd_validate2.cli";
			}
			leaf address {
				type string {
					configd:syntax "/opt/vyatta/share/tmplscripts/policy/qos/shaper/class/match/source/address/configd_syntax1.cli";
				}
				configd:help "Source IP subnet";
			}
			leaf port {
				type string {
					configd:syntax "/opt/vyatta/share/tmplscripts/policy/qos/shaper/class/match/source/port/configd_syntax1.cli";
				}
				configd:help "Source port";
				configd:validate "/opt/vyatta/share/tmplscripts/policy/qos/shaper/class/match/source/port/configd_validate1.cli";
			}
		}
		leaf log {
			type empty;
			configd:help "Enable logging for QoS rule";
		}
		container destination {
			presence "true";
			configd:help "Destination parameters";
			leaf mac-address {
				type types:mac-address;
				configd:help "Destination MAC address";
				configd:validate "/opt/vyatta/share/tmplscripts/policy/qos/shaper/class/match/destination/mac-address/configd_validate1.cli";
				configd:validate "/opt/vyatta/share/tmplscripts/policy/qos/shaper/class/match/destination/mac-address/configd_validate2.cli";
			}
			leaf address {
				type string {
					configd:syntax "/opt/vyatta/share/tmplscripts/policy/qos/shaper/class/match/destination/address/configd_syntax1.cli";
				}
				configd:help "Destination IP subnet";
			}
			leaf port {
				type string {
					configd:syntax "/opt/vyatta/share/tmplscripts/policy/qos/shaper/class/match/destination/port/configd_syntax1.cli";
				}
				configd:help "Destination port";
				configd:validate "/opt/vyatta/share/tmplscripts/policy/qos/shaper/class/match/destination/port/configd_validate1.cli";
			}
		}
		leaf dscp {
			type dscp:dscp-name-or-value;
			configd:help "DSCP value to match in an incoming IP header";
		}
		leaf protocol {
			type string {
				configd:syntax "/opt/vyatta/share/tmplscripts/policy/qos/shaper/class/match/protocol/configd_syntax1.cli";
			}
			configd:help "Protocol to match";
			configd:allowed "/opt/vyatta/share/tmplscripts/policy/qos/shaper/class/match/protocol/configd_allowed.sh";
		}
	}

	grouping class-list {
		list class {
			configd:help "Class number";
			max-elements "1048576";
			key "tagnode";
			leaf tagnode {
				type uint32 {
					range 1..999999;
				}
				configd:help "Class number (1-999999)";
			}
			leaf description {
				type string;
				configd:help "Description for this policy class";
			}
			leaf profile {
				type name;
				configd:help "QoS profile for class [REQUIRED]";
				configd:allowed "echo $VAR(../../profile/@@)";
			}
			list match {
				configd:help "Class matching rule";
				key "tagnode";
				leaf tagnode {
					type name;
					configd:help "Class matching rule";
				}
				uses match-rule;
			}
		}
	}

	grouping traffic-class-list {
		list traffic-class {
			configd:help "Traffic Class";
			key "tagnode";
			leaf tagnode {
				type uint32 {
					range 0..3;
				}
				configd:help "Traffic Class";
			}
			leaf description {
				type string;
				configd:help "Description for this traffic-class";
			}

			leaf bandwidth {
				type union {
					type bandwidth-suffix;
					type bandwidth-percent;
				}
				default "100%";
				configd:help "Bandwidth limit";
			}
			leaf burst {
				type burst-size;
				configd:help "Burst size in bytes";
			}
		}
	}

	grouping subport-parameters {
		leaf default {
			type name;
			configd:help "Qos profile for default traffic";
			configd:allowed "echo $VAR(../profile/@@)";
		}
		leaf burst {
			type burst-size;
			configd:help "Burst size";
		}
		leaf period {
			type uint32 {
				range 1..3000;
			}
			configd:help "Enforcement period (ms)";
			default "40";
		}
	}

	grouping red-parameter {
		container random-detect {
			presence "true";
			configd:help "Random Early Detection (RED) parameters";
			leaf min-threshold {
				type uint16 {
					range 1..1022;
				}
				configd:help "Minimum threshold";
			}
			leaf max-threshold {
				type uint16 {
					range 1..1023;
				}
				configd:help "Maximum threshold";
			}
			leaf filter-weight {
				type uint16 {
					range 1..12;
				}
				configd:help "EWMA Filter Weight";
				default "9";
			}
			leaf mark-probability {
				type uint16 {
					range 1..255;
				}
				configd:help "Inverse of packet marking probability maximum value";
				default "10";
			}
		}
	}

	augment /policy:policy {
		list qos {
			configd:priority "400";
			configd:help "Quality of Service (QOS) policy";
			configd:validate "qos-policy.pl --validate $VAR(@)";
			configd:end "qos-policy.pl --update $VAR(@)";

			key "tagnode";
			leaf tagnode {
				type name;
				configd:help "Quality of Service (QOS) policy";
			}
			container shaper {
				configd:help "Shaping QOS policy";
				list vlan {
					configd:help "Virtual Local Area Network (VLAN) ID";
					key "tagnode";
					leaf tagnode {
						type uint16 {
							range 1..4094;
						}
						configd:help "Virtual Local Area Network (VLAN) ID";
					}
					leaf description {
						type string;
						configd:help "Description for this vlan";
					}
					leaf bandwidth {
						type union {
							type bandwidth-suffix;
							type bandwidth-percent;
						}
						default "100%";
						configd:help "Bandwidth limit";
					}
					uses subport-parameters;
					uses traffic-class-list;
					uses class-list;
				}
				leaf description {
					type string;
					configd:help "Description for this QoS policy";
				}
				leaf frame-overhead {
					type uint32 {
						range 0..1000;
					}
					configd:help "Framing overhead";
					default "24";
				}
				list profile {
					configd:help "QoS traffic profile";
					max-elements "256";
					key "tagnode";
					leaf tagnode {
						type name;
						configd:help "QoS traffic profile";
					}
					leaf period {
						type uint32 {
							range 1..3000;
						}
						configd:help "Enforcement period (ms)";
						default "10";
					}
					leaf description {
						type string;
						configd:help "Description for this traffic profile";
					}

					leaf burst {
						type burst-size;
						configd:help "Burst size in bytes";
					}
					leaf bandwidth {
						type bandwidth-suffix;
						configd:help "Bandwidth limit";
					}

					container map {
						configd:help "Type to queue mapping";
						list pcp {
							configd:help "Priority Control Point";
							key "tagnode";
							leaf tagnode {
								type uint32 {
									range 0..7;
								}
								configd:help "Priority Control Point";
							}
							leaf to {
								type uint32 {
									range 0..7;
								}
								configd:help "Queue [REQUIRED]";
							}
						}
						list dscp {
							configd:help "DSCP to queue mapping";
							key "tagnode";
							leaf tagnode {
							    type dscp-name;
								configd:help "DSCP value";
							}
							leaf to {
								type uint32 {
									range 0..7;
								}
								configd:help "Queue [REQUIRED]";
							}
						}
					}
					list queue {
						configd:help "Queue properties";
						key "tagnode";
						leaf tagnode {
							type uint32 {
								range 0..7;
							}
							configd:help "Queue properties";
						}
						leaf description {
							type string;
							configd:help "Description for this queue";
						}
						leaf traffic-class {
							type uint32 {
								range 0..3;
							}
							configd:help "Traffic class";
						}
						leaf weight {
							type uint8 {
								range 1..100;
							}
							configd:help "WRR weight";
							default "1";
						}
					}
					uses traffic-class-list;
				}

				list traffic-class {
					configd:help "Traffic Class";
					key "tagnode";
					leaf tagnode {
						type uint32 {
							range 0..3;
						}
						configd:help "Traffic Class";
					}
					leaf description {
						type string;
						configd:help "Description for this traffic-class";
					}
					leaf bandwidth {
						type union {
							type bandwidth-suffix;
							type bandwidth-percent;
						}
						default "100%";
						configd:help "Bandwidth limit";
					}
					leaf burst {
						type burst-size;
						configd:help "Burst size in bytes";
					}
					leaf queue-limit {
						type uint16 {
							range 1..max;
							configd:syntax "/opt/vyatta/share/tmplscripts/policy/qos/shaper/traffic-class/queue-limit/configd_syntax1.cli";
						}
						configd:help "Queue size";
						default "64";
					}
					uses red-parameter;
				}
				leaf bandwidth {
					type bandwidth-suffix;
					default "10Gbit";
					configd:help "Bandwidth limit";
				}
				uses subport-parameters;
				uses class-list;
			}
		}
	}

	augment /if:interfaces/interfaces-dataplane:dataplane {
		leaf qos-policy {
			type string;
			configd:help "Qos policy for interface";
			configd:allowed "echo $VAR(/policy/qos/@@)";
			configd:update "qos-policy.pl --apply $VAR(../@) $VAR(@)";
			configd:delete "qos-policy.pl --remove $VAR(../@)";
			configd:validate "/opt/vyatta/share/tmplscripts/interfaces/dataplane/qos-policy/configd_validate1.cli";
		}
	}
}
