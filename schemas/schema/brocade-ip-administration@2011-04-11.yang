/***********************************************************
 * Brocade Ip administration Data model
 *
 * May 2011,Arun kumar viswanathan
 *
 * Copyright (c) 2011 by Brocade Communications Systems, Inc.
 * All rights reserved.
 *
 ************************************************************/

module brocade-ip-administration {
    namespace "urn:brocade.com:mgmt:brocade-ip-administration";
    prefix ip-administration;

    /* Linkage Statements */

    import ietf-inet-types {
        prefix inet;
    }

    import brocade-common-def {
        prefix common-def;
    }

    import tailf-common {
        prefix tailf;
    }

    /* Meta Information */

    organization
        "Brocade Communications Systems, Inc.";

    contact
        "Brocade Communications Systems, Inc.
         Postal: 130 Holger Way
                 San Jose, CA 95134
                 U.S.A
         Tel: +1-408-333-8000
         E-mail: support@Brocade.com
         web: www.brocade.com.";

    description
        "This management module is an instrumentation to ipadm
         level commands";

    /* Revision history */

    revision "2011-04-11" {
        description
            "Initial version of this management module.";
    }

    /* Module Definition */

    augment "/common-def:ip" {
        description "IP Configurations";
        container dns {
            container dom-name {
		leaf domain-name {
                mandatory false; 
                type string;
               }
            }
            list name-server {
                max-elements 2;
                key "name-server-ip";
                leaf name-server-ip {
                    type inet:ip-address;
                }
            }
        }
    }
}
