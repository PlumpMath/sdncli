/*********************************************************************
* brocade-default-config.yang: Model that will contain default-config
* enable/disable settings
*
* Copyright (c) 2014 by Brocade Communications Systems, Inc.
* All rights reserved.
**********************************************************************/

module brocade-default-config {
    //namespace "urn:brocade.com:mgmt:brocade-default-config";
    namespace "http://brocade.com/ns/brocade-default-config";
    prefix "brocade-default-config";

    import tailf-common {
        prefix tailf;
    }

    import brocade-rbridge { 
        prefix rbridge;
    }

    description 
        "Module for enabling default configuration CLIs";   

	grouping default-config-cmds {
		container default-config {

            leaf enable {
                type empty;
            }
		}
	}

	augment "/rbridge:rbridge-id" {
		uses default-config-cmds;
	}
}
