/***********************************************************************
 * brocade-clock.yang: Brocade Clock data model
 *
 * Feb 2011, Newton Oku
 *
 * Copyright (c) 2011 by Brocade Communications Systems, Inc.
 * All rights reserved.
 *
 **********************************************************************/

module brocade-clock {
    namespace "urn:brocade.com:mgmt:brocade-clock";
    prefix clock-server;

    import tailf-common {
        prefix tailf;
    }

    import ietf-yang-types {
        prefix ietfyang;
    }

    import brocade-common-def {
        prefix common-def;
    }

    import brocade-rbridge {
        prefix rbridge;
    }

    organization
        "Brocade Communications Systems, Inc.";

        contact
        "Brocade Communications Systems, Inc.
         Postal: 130 Holger Way
                 San Jose, CA 95134
                  U.S.A
         Tel: +1-408-333-8000
         E-mail: support@Brocade.com
         web: www.brocade.com.";

        description
        "An instrumentation to configure local clock.";

        revision "2009-05-01" {
        description
            "Initial version of this module.";
    }


    container clock-set-datetime {
        tailf:action clock {
            input {
                leaf set {
                    type ietfyang:date-and-time;
                    mandatory true;
                }
                leaf rbridge-id {
                    mandatory false;
                    type common-def:rbridge-id-all-type;
                }
            }
            output {
            }
        }
    }

    container clock-set-timezone {
        tailf:action clock {
            input {
                leaf timezone {
                    type common-def:timezone;
                    mandatory true;
                }
                leaf rbridge-id {
                    mandatory false;
                    type common-def:rbridge-id-all-type;
                }
            }
            output {
            }
        }
    }

    augment "/common-def:no" {
        container clock {
            tailf:action timezone {
                input {
                    leaf rbridge-id {
                        mandatory false;
                        type common-def:rbridge-id-all-type;
                    }
                }
                output {
                }
            }
        }
    }

    grouping timezone-group {
        container clock {
            leaf timezone {
                type common-def:timezone;
            }
        }
    }

    augment "/rbridge:rbridge-id" {
        uses timezone-group;
    }

    container clock-sa {
        uses timezone-group;
    }

    rpc show-clock {
        description
            "display current time for the cluster or specified switch";
        input {
            leaf rbridge-id {
                mandatory false;
                type common-def:rbridge-id-all-type;
            }
        }
        output {
            list clock-time {
                leaf rbridge-id-out {
                    type common-def:rbridge-id-type;
                }
                leaf current-time {
                    type ietfyang:date-and-time;
                    description
                        "switch date and time";
                }
                leaf timezone {
                    type string {
                        length "3 .. 100";
                    }
                    description
                        "region/city or region/state/city";
                }
            }
        }
    }
}
