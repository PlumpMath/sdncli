/***********************************************************************
 * brocade-beacon.yang: Brocade Beacon Management Module.
 *
 * July 2011,  Hung Nguyen
 *
 * Copyright (c) 2011, 2012 by Brocade Communications Systems, Inc.
 * All rights reserved.
 *
 **********************************************************************/
module brocade-beacon {
	namespace "urn:brocade.com:mgmt:brocade-beacon";
	prefix "beacon";
		
	import tailf-common {
		prefix tailf;
	}

	revision "2011-10-31" {
	    description     
	       "Initial version of this management module.";
	}
	
    /* define the "beacon operations" functionality */
	container beacon {
		container enable {
			tailf:action interface {
				input {
					choice interface-type {	
					case fortygigabitethernet { 
						leaf fortygigabitethernet {
							type string { 
								length "3..16"  {
								}
							}
							mandatory true;
						}
					}
					case hundredgigabitethernet { 
						leaf hundredgigabitethernet {
							type string { 
								length "3..16"  {
								}
							}
							mandatory true;
						}
					}
					case gigabitethernet {
						leaf gigabitethernet {
							type string {
								length "3..16"  {
								}
							}
							mandatory true;
						}
					}
					case tengigabitethernet {
						leaf tengigabitethernet {
							type string { 
								length "3..16"  {
								}
							}
							mandatory true;
						}
					}
					}
				}
				output {}
			}
			tailf:action chassis {
				input {}
				output {}	
			}  
		}	/* End of Action Enable */

		container disable {
			tailf:action interface {
				input {
					choice interface-type {	
					case fortygigabitethernet { 
						leaf fortygigabitethernet {
							type string { 
								length "3..16"  {
								}
							}
							mandatory true;
						}
					}
					case hundredgigabitethernet { 
						leaf hundredgigabitethernet {
							type string { 
								length "3..16"  {
								}
							}
							mandatory true;
						}
					}
					case gigabitethernet {
						leaf gigabitethernet {
							type string {
								length "3..16"  {
								}
							}
							mandatory true;
						}
					}
 
					case tengigabitethernet {
						leaf tengigabitethernet {
							type string { 
								length "3..16"  {
								}
							}
							mandatory true;
						}
					}
					}
				}
				output {}
			}
			tailf:action chassis {
				input {}
				output {}
			}
		}   /* End of Action Disable */

	} /* End of Beacon Container */
}
