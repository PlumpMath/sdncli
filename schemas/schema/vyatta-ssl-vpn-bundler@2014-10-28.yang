module vyatta-ssl-vpn-bundler {
	namespace "urn:vyatta.com:mgmt:vyatta-ssl-vpn-bundler";
	prefix ssl-vpn-bundler;

	import vyatta-interfaces {
		prefix if;
	}
	import vyatta-interfaces-openvpn {
		prefix interfaces-openvpn;
	}
	import configd {
		prefix configd;
	}

	organization "Brocade Communications Systems, Inc.";
	contact
		"Brocade Communications Systems, Inc.
		 Postal: 130 Holger Way
		         San Jose, CA 95134
		 E-mail: support@Brocade.com
		 Web: www.brocade.com";

	revision 2014-10-28 {
		description "Update for 3.2.1R1";
	}
	
	revision 2014-10-23 {
		description "Initial revision.";
		configd:migration 1;
	}

	augment /if:interfaces/interfaces-openvpn:openvpn {
		container client-bundle {
			presence "true";
			configd:help "Generate SSL-VPN Client Bundles";
			leaf osx {
				type empty;
				configd:help "Generate OpenVPN formatted config file for OS X OpenVPN clients";
			}
			leaf linux {
				type empty;
				configd:help "Generate SSL-VPN Client Bundle for Linux";
			}
			leaf windows {
				type empty;
				configd:help "Generate SSL-VPN Client Bundle for Windows";
			}
			leaf generic {
				type empty;
				configd:help "Generate standard OpenVPN formatted config file with CA certificate inline";
			}
		}
	}
}
