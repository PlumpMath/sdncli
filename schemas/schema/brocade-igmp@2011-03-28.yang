/***********************************************************************
 * brocade-igmp : Brocade IGMP data model
 *
 * March 2011, Abhay Gidwani
 *
 * Copyright (c) 2011 by Brocade Communications Systems, Inc.
 * All rights reserved.
 *
 **********************************************************************/

module brocade-igmp {
    namespace "urn:brocade.com:mgmt:brocade-igmp";
    prefix igmp;

    
    import brocade-rbridge { prefix rbridge; }
    import brocade-interface { prefix interface;}
    import brocade-ip-config { prefix ip-config;}
    import brocade-igmp-snooping { prefix igmp-snooping; }
    import tailf-common { prefix "tailf"; }
    import ietf-inet-types  { prefix "inet"; }

    organization
        "Brocade Communications Systems, Inc.";

    contact           
        "Brocade Communications Systems, Inc.
        130 Holger Way,
        San Jose, CA 95134
        U.S.A
        Tel: +1-408-333-8000
        E-mail: info@brocade.com
        Web: www.brocade.com";

    description       
        "This file defines the data model for the IGMP (Internet
        Group Management Protocol) configuration commands.";

    revision "2011-03-28" {
        description     
            "Initial version of the IGMP module.";
    }         

	/* Module Definition */

    grouping igmp-phy-intf-cfg-cmd {
        container igmp-phy-intf-cfg {
            container igmp {

                leaf last-member-query-interval {
                    type igmp-snooping:lmqt-type;
                    units "milliSeconds";
                    default 1000;
                }

                leaf query-interval {
                    type igmp-snooping:qi-type;
                    units "Seconds";
                    default 125;
                }

                leaf query-max-response-time {
                    type igmp-snooping:qmrt-type;
                    units "Seconds";
                    default 10;
                }

                leaf immediate-leave {
                    type empty;
                }
                list static-group {

                    key "sg-addr";

                    leaf sg-addr {
                        type inet:ipv4-address;
                    }
                }
            }
        }
    }
    
    grouping igmp-po-intf-cfg-cmd {
        container igmp-po-intf-cfg {
            container igmp {

                leaf last-member-query-interval {
                    type igmp-snooping:lmqt-type;
                    units "milliSeconds";
                    default 1000;
                }

                leaf query-interval {
                    type igmp-snooping:qi-type;
                    units "Seconds";
                    default 125;
                }

                leaf query-max-response-time {
                    type igmp-snooping:qmrt-type;
                    units "Seconds";
                    default 10;
                }

                leaf immediate-leave {
                    type empty;
                }
                list static-group {

                    key "sg-addr";

                    leaf sg-addr {
                        type inet:ipv4-address;
                    }
                }
            }
        }
    }

	grouping vlan_igmp_cmds {
		container igmp {

			leaf last-member-query-interval {
				type igmp-snooping:lmqt-type;
                units "milliSeconds";
                default 1000;
			}

			leaf query-interval {
				type igmp-snooping:qi-type;
                units "Seconds";
                default 125;
			}

			leaf query-max-response-time {
                type igmp-snooping:qmrt-type;
                units "Seconds";
                default 10;
			}

            leaf immediate-leave {
                type empty;
            }
			list static-group {

				key "sg-addr";

				leaf "sg-addr" {
					type inet:ipv4-address;
				}
            }
        }
    }
   
    augment "/rbridge:rbridge-id/interface:interface/interface:ve/ip-config:ip" {
    	uses vlan_igmp_cmds; 
    }
    
   	/*augment "/interface:interface-vlan/interface:interface/interface:ve/interface:ip" {
		uses vlan_igmp_cmds {
			refine "igmp" {
			}
		}
    }*/
    
    augment "/interface:interface/interface:gigabitethernet/interface:ip" {
		description "Internet Protocol (IP)";
        uses igmp-phy-intf-cfg-cmd;
    }

    augment "/interface:interface/interface:tengigabitethernet/interface:ip" {
		description "Internet Protocol (IP)";
        uses igmp-phy-intf-cfg-cmd;
    }

    augment "/interface:interface/interface:fortygigabitethernet/interface:ip" {
		description "Internet Protocol (IP)";
        uses igmp-phy-intf-cfg-cmd;
    }

    augment "/interface:interface/interface:hundredgigabitethernet/interface:ip" {
        description "Internet Protocol (IP)";
        uses igmp-phy-intf-cfg-cmd;
    }

   /*	augment "/interface:interface/interface:port-channel/interface:ip" {
		container hide-igmp-holder {
			uses igmp-po-intf-cfg-cmd;
    	} 
    }*/

}
