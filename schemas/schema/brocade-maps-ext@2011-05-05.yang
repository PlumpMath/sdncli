/***********************************************************************
 * brocade-maps-ext.yang: data model for show system-monitor
 *
 * May 2011, Priya Ahuja
 *
 * Copyright (c) 2011 by Brocade Communications Systems, Inc.
 * All rights reserved.
 *
 **********************************************************************/
module brocade-maps-ext {
    namespace "urn:brocade.com:mgmt:brocade-maps-ext";
    prefix "maps-extensions";
  
    import tailf-common {
        prefix tailf;
    }

    import ietf-inet-types {
        prefix inet;
    }

    import ietf-yang-types {
        prefix ietfyang;
    }

    import brocade-common-def {
        prefix common-def;
    }


    organization
        "Brocade Communications Inc.";

    contact
        "Brocade Communications Systems, Inc.
         Postal: 130 Holger Way
                 San Jose, CA 95134
                 U.S.A
         Tel: +1-408-333-6061
         E-mail: support@Brocade.com
         web: www.brocade.com.";

    description
        "This sub module defines show system-monitor data model
         Copyright (c) 2011 by Brocade Communications Systems, Inc.
         All rights reserved.";

    revision 2011-05-05 {
        description
          "Initial version of this module.";
    }

    augment "/common-def:show" {
        container mapstmp {
            tailf:action maps {
            input {
				leaf type {
					type enumeration {
						enum dashboard;
					}
				}
                leaf rbridge-id {
                    mandatory false;
                    type common-def:rbridge-id-all-type;
                }
            }
            output {
            }
        }
      }
    }
	rpc maps-get-all-policy {
		description
		   "Shows the existing MAPS Policies";

		input {
			leaf rbridge-id{
			   type common-def:rbridge-id-all-type;
			}
		}
		output {
			list policy {
				leaf policyname {
					type string;
					description "MAPS Policy name";
				}
			}
		}
	}
	rpc maps-get-rules {
		description
		   "Shows the existing MAPS Policies";

		input {
			leaf rbridge-id{
			   type common-def:rbridge-id-all-type;
			}
		}
		output {
			list rules {
				leaf rulename {
					type string;
					description "MAPS Rule name";
				}
				leaf groupname {
					type string;
					description "MAPS Group name";
				}
				leaf monitor {
					type string;
					description "MAPS Monitor name";
				}
				leaf op {
					type string;
					description "MAPS operator";
				}
				leaf value {
					type string;
					description "MAPS threshold value";
				}
				leaf action {
					type string;
					description "MAPS action value";
				}
				leaf timebase {
					type string;
					description "MAPS timebase value";
				}
				leaf policyname {
				   type string;
				   description "MAPS policy associated with rule";
				}
			}
		}
	}
}
