/***********************************************************************
 *brocade-maps.yang-: Brocade MAPS Data Model
 *
 *  2014, D. Chung
 *
 * Copyright (c) 2011-2014 by Brocade Communications Systems, Inc.
 * All rights reserved.
 *
 **********************************************************************/
module brocade-maps {
    namespace "urn:brocade.com:mgmt:brocade-maps";
    prefix "maps";

    import tailf-common {
        prefix tailf;
    }
   
    import ietf-inet-types {
        prefix inet;
    }
 
    import brocade-rbridge {
        prefix rbridge;
    }

    import brocade-interface {
       prefix interface;
    }

    organization
        "Brocade Communications Systems, Inc.";

    contact           
        "Brocade Communications Systems, Inc.
         Postal: 130 Holger Way
                 San Jose, CA 95134
                 U.S.A
         Tel: +1-408-333-8000
         E-mail: support@Brocade.com 
         web: www.brocade.com.";

    description       
        "This management module is an instrumentation to manage MAPS 
         feature.";

    typedef port-type {
        type string {
            length "1..16"  {
            }
        }
    }

    typedef wwn-type {
        type string {
            pattern '([0-9a-f]{2}(:[0-9a-f]{2}){7})|([a,A][n.N][y,Y])|([n,N][o,O][n,N][e,E])';
        }
        description
            "World Wide Name (Only lower case allowed)";
    }

    typedef maps-action-type {
        type bits {
            bit NONE { position 0; }
            bit SNMP { position 1; }
            bit EMAIL { position 2; }
            bit FENCE { position 3; }
            bit SW_CRITICAL { position 4; }
            bit SW_MARGINAL { position 5; }
            bit SFP_MARGINAL { position 6; }
            bit RASLOG  { position 7; }
        }
    }
	grouping common-phy-maps-cmds {
		container connectivity {
			leaf deviceconnectivity {
	            type enumeration {
					enum None {
						value 0;
					}
    	            enum iSCSI {
						value 1;
                	}
    	            enum NAS {
						value 2;
                	}
    	            enum DAS {
						value 3;
                	}
            	}
				default None;
			}
		}
	}
    augment "/rbridge:rbridge-id" {
	container maps {

		container enable {

			leaf policy {
				type string {
				}
			}

			leaf actions {
				type maps-action-type;
				default NONE;
			}	
		}
		container email {
			list email-list {
                key "email";
                max-elements 5;
                leaf email {
                    type string;
                }
			}
		}
		list relay {
            max-elements 1;
			key "hostip";
			leaf hostip {
				type inet:host;
			}
			leaf domainname {
                type string;
				mandatory true; 
			}
		} 
	}
}
    augment "/interface:interface/interface:tengigabitethernet" {
		uses common-phy-maps-cmds;	
	}
    augment "/interface:interface/interface:gigabitethernet" {
        uses common-phy-maps-cmds ;
    }

    augment "/interface:interface/interface:fortygigabitethernet" {
        uses common-phy-maps-cmds;
    }

    augment "/interface:interface/interface:hundredgigabitethernet" {
        uses common-phy-maps-cmds;
    }

}
