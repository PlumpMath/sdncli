/*
 * Copyright (c) 2012-2014 by Brocade Communications Systems, Inc. All Rights Reserved.
 * 
 * This software is licensed, and not freely redistributable. See the
 * license agreement for details.
*/
module path-provider-impl {

    yang-version 1;
    namespace "urn:opendaylight:params:xml:ns:yang:controller:config:path-provider:impl";
    prefix "path-provider-impl";

    import config { prefix config; revision-date 2013-04-05; }
    import opendaylight-md-sal-binding { prefix mdsal; revision-date 2013-10-28; }
    import opendaylight-md-sal-dom { prefix dom; revision-date 2013-10-28; }

    description
        "This module contains the base YANG definitions for
        path-provider impl implementation.";

    revision "2014-05-23" {
        description
            "Initial revision.";
    }

    // This is the definition of the service implementation as a module identity.
    identity path-provider-impl {
            base config:module-type;

            // Specifies the prefix for generated java classes.
            config:java-name-prefix PathProvider;
    }

    // Augments the 'configuration' choice node under modules/module.  
    // We consume the three main services, RPCs, DataStore, and Notifications 
    augment "/config:modules/config:module/config:configuration" {
        case path-provider-impl {
            when "/config:modules/config:module/config:type = 'path-provider-impl'";
    
            container rpc-registry {
                uses config:service-ref {
                    refine type {
                        mandatory true;
                        config:required-identity mdsal:binding-rpc-registry;
                    }
                }
            }
    
            container notification-service {
                uses config:service-ref {
                    refine type {
                        mandatory true;
                        config:required-identity mdsal:binding-notification-service;
                    }
                }
            }
    
            container data-broker {
                uses config:service-ref {
                    refine type {
                        mandatory false;
                        config:required-identity mdsal:binding-async-data-broker;
                    }
                }
            }
            
            container data-broker-old {
                uses config:service-ref {
                    refine type {
                        mandatory false;
                        config:required-identity mdsal:binding-data-broker;
                    }
                }
            }
            
            container dom-data-broker {
                uses config:service-ref {
                    refine type {
                        mandatory false;
                        config:required-identity dom:dom-async-data-broker;
                    }
                }
            }
            
            
        }
    }
}
