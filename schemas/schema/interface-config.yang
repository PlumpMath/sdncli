// YANG submodule for interface configuration definitions.
// Revisions:
//     2011-04-20: Initial version.
//

submodule interface-config
{
    belongs-to netiron-config 
    {
        prefix brcd;
    }
    
    import common-defs
    {
        prefix "common";
    }

    
    organization 
        "Brocade Communications Inc.";

    contact 
             "Technical Support Center"+
             "130 Holger Way,"+
             "San Jose, CA  95134"+
             "Email:  ipsupport@brocade.com"+
             "Phone: 1-800-752-8061"+
             "URL:  www.brocade.com";

    description "This module defines the Interface configuration. VERSION: V5.8.00a";
    
    revision 2011-04-20
    {
        description "Initial revision";
    }

    typedef interface_speed_duplex 
    {
        type enumeration 
        {
            enum auto 
            {
                value "1";
                description "Autonegotiation";
            }
            enum 10-full 
            {
                value "2";
                description "10M, full duplex";
            }
            enum 10-half 
            {
                value "3";
                description "10M, half duplex";
            }
            enum 100-full 
            {
                value "4";
                description "100M, full duplex";
            }
            enum 100-half 
            {
                value "5";
                description "100M, half duplex";
            }
            enum 1000-full 
            {
                value "6";
                description "1G, full duplex";
            }
            enum 1000-half 
            {
                value "7";
                description "1G, half duplex";
            }
            enum 1000-master 
            {
                value "8";
                description "1G, master";
            }
            enum 1000-slave 
            {
                value "9";
                description "1G, slave. The 1000-slave speed duplex is"
                          + " applicable only for CES/CER devises";
            }
        }
        description "Speed duplex";
    }


    grouping interface-config-grouping
    {
        description "Interface configuration group";
        container interface-config
        {
	    description "Interface configuration";
            list interface
            {
                key interface-id;
                description "List of Interfaces configured "+
                            "on the system";
                leaf interface-id
                {
                    type common:interface-all-types;
                    description "Single or group of interfaces";
                }
             
                leaf alarm-monitoring
                {
                    type empty;
                    description "Enable alarm monitoring";
                }
            
                choice admin-status-choice
                {
                    description "Enable/Tear down the LSP";
                 
                    case enable
                    {
                        leaf enable
                        {
                            type empty;
                            description "Enable the LSP";
                        }
                    }
                    case disable
                    {
                        leaf disable
                        {
                            type empty;
                            description "Tear down the LSP";
                        }
                    }
                } // end choice admin-status-choice
            
                container gig-default
                {
                    description "Global Gig port default options";
                    choice gig-default-option
                    {
                        description "Gig default type";
                        case auto-gig
                        {
                            leaf auto-gig
                            {
                                type empty;
                                description "Autonegotiation";
                            }
                        }
                        case neg-off
                        {
                            leaf neg-off
                            {
                                type empty;
                                description "Non-Autonegotiation";
                            }
                        }
                        case auto-full
                        {
                            leaf auto-full
                            {
                                type empty;
                                description " Full Autonegotiation";
                            }
                        }
                        case neg-full-auto
                        {
                            leaf neg-full-auto
                            {
                                type empty;
                                description "Autonegotiation first, "+
				    "if failed try non-autonegotiation";

                            }
                        }
                    } //end choice gig-default-option
                    
                } //end container gig-default
                
                leaf route-only
                {
                    type empty;
                    description "Enable Layer 2 switching";
                }
            
                container drop-precedence
                {
                    description "QOS drop precedence";
                    leaf value
                    {
                        type uint32
                        {
                            range "0..3";
                        }
                        description "Drop precedence value";
                    }
                    leaf force
                    {
                        type empty;
                        description "Drop precedence force";
                       
                    }
                } //end container drop-precedence
            
                container loop-detection 
                {
                    description "Shutdown this port if receiving "+
                             "packets originated from this port";
                    leaf vlan
                    {
                        type common:vlan-identifier;
                        description "Loop detection for this vlan";
                    }
                    
                    leaf shutdown-disable
                    {
                        type empty;
                        description "Disable shutdown by "+
                        	    "loop detection";
                    }
                
                    leaf shutdown-sending-port
                    {
                        type empty;
                        description "Shutdown the sending port";
                    }
                } //end container loop-detection
            
                leaf load-interval
                {
                    type uint32
                    {
                        range "30..300";
                    }
                    units "Seconds";
                    description "Load interval, multiple of 30";
                }
	    
        	leaf source-guard
        	{
        	    type empty;
        	    description "Enable/ IP source guard";
        	}
          
                leaf flow-control
                {
                    type empty;
                    description "Enable 802.3 flow control "+
                              "on full duplex port";
                }
                
                leaf speed-duplex
                {
                    type interface_speed_duplex;
                    description "Speed duplex for this interface"; 
                }
            
                container ip
                {
                    description "Interface IPv4 configuration";
                    leaf address
                    {
                        type common:ipv4_address_mask;
                        description "IPv4 address";
                    }
                } //end container ip

                container ipv6
                {
                    description "Interface IPv6 configuration";
                    leaf address
                    {
                        type common:ipv6_address_mask;
                        description "IPv6 address";
                    }
                    leaf enable
                    {
                        type empty;
                        description "Enable IPv6 on this interface";
                    }
                } //end container ipv6
                
                uses common:priority-grouping;
                
            } //end list interface
                
         } //end container interface-config
        
    } //end grouping interface-config-grouping
    
} //end submodule interface-config
